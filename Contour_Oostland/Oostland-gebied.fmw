FME workspace Oostland-gebied.fmw
Title: Oostland-gebied
Description: Deze workspace genereert een zip-bestand met daarin
- een contour van het Oostland-gebied,
- de gemeenten binnen het Oostland-gebied,
- alle buurten binnen het Oostland-gebied
in shape-formaat in RD New.
History: ,18-2-2019,Willy Tadema,

Parameters:
- DestDataset_ESRISHAPE = C:\Temp\Oostland.zip   # Destination Esri Shapefile Folder
- SourceDataset_WFS = https://geodata.nationaalgeoregister.nl/bestuurlijkegrenzen/wfs?   # Source WFS (Web Feature Service) URL

Readers:
- WFS_1: WFS from $(SourceDataset_WFS) in EPSG:28992

Writers:
- ESRISHAPE_1: ESRISHAPE to $(DestDataset_ESRISHAPE)

Note: Alleen gemeenten in Oostland
gemeenten (reader WFS_1)
    attributes: gml_parent_id xml_buffer, gml_parent_property xml_buffer, gml_id xml_buffer, code xml_buffer, code.xsi_nil xml_boolean, gemeentenaam xml_buffer, gemeentenaam.xsi_nil xml_boolean, geom xml_geometry
    -> Dissolver
    -> Bufferer
    -> AttributeKeeper_2
Dissolver
    ACCUM_INPUT_ATTRS = Use Attributes From One Feature
    CLEANING_TOLERANCE = None
    CONNECT_Z_MODE = First Wins
    DEAGGREGATE_INPUT = Yes
    NO_OVRLP = No
    AREA -> AttributeKeeper
AttributeKeeper
    -> Oostland_contour (writer ESRISHAPE_1)
Oostland_contour (writer ESRISHAPE_1)
AttributeKeeper_2
    -> Oostland_gemeenten (writer ESRISHAPE_1)
Oostland_gemeenten (writer ESRISHAPE_1)
Bufferer
    ANGLE = 22.5
    CAP_STYLE = Round
    CORNER_STYLE = Round
    MODE = AREA
    OFFSET = 100
    BUFFERED -> FeatureReader [INITIATOR]
Oostland_buurten (writer ESRISHAPE_1)
    attributes: buurtcode char(200), buurtnaam char(200), gemeenteco char(200), gemeentena char(254), wijkcode char(200)

Bookmark: Buurten in het Oostland
FeatureReader
    ATTRIBUTES = cbs_buurten_2017,"gml_parent_id,gml_parent_property,gml_id,aantal_inwoners,aantal_inwoners.xsi_nil,mannen,mannen.xsi_nil,vrouwen,vrouwen.xsi_nil,aantal_huishoudens,aantal_huishoudens.xsi_nil,bevolkingsdichtheid_inwoners_per_km2,bevolkingsdichtheid_inwoners_per_km2.xsi_nil,buurtcode,buurtcode.xsi_nil,buurtnaam,buurtnaam.xsi_nil,dekkingspercentage,dekkingspercentage.xsi_nil,gemiddelde_huishoudsgrootte,gemiddelde_huishoudsgrootte.xsi_nil,gemeentecode,gemeentecode.xsi_nil,gemeentenaam,gemeentenaam.xsi_nil,indelingswijziging_wijken_en_buurten_indicator,indelingswijziging_wijken_en_buurten_indicator.xsi_nil,omgevingsadressendichtheid,omgevingsadressendichtheid.xsi_nil,oppervlakte_land_in_ha,oppervlakte_land_in_ha.xsi_nil,oppervlakte_totaal_in_ha,oppervlakte_totaal_in_ha.xsi_nil,oppervlakte_water_in_ha,oppervlakte_water_in_ha.xsi_nil,percentage_personen_0_tot_15_jaar,percentage_personen_0_tot_15_jaar.xsi_nil,percentage_personen_15_tot_25_jaar,percentage_personen_15_tot_25_jaar.xsi_nil,percentage_personen_25_tot_45_jaar,percentage_personen_25_tot_45_jaar.xsi_nil,percentage_personen_45_tot_65_jaar,percentage_personen_45_tot_65_jaar.xsi_nil,percentage_personen_65_jaar_en_ouder,percentage_personen_65_jaar_en_ouder.xsi_nil,percentage_uit_nederlandse_antillen_en_aruba,percentage_uit_nederlandse_antillen_en_aruba.xsi_nil,percentage_eenpersoonshuishoudens,percentage_eenpersoonshuishoudens.xsi_nil,percentage_gehuwd,percentage_gehuwd.xsi_nil,percentage_gescheid,percentage_gescheid.xsi_nil,percentage_huishoudens_met_kinderen,percentage_huishoudens_met_kinderen.xsi_nil,percentage_huishoudens_zonder_kinderen,percentage_huishoudens_zonder_kinderen.xsi_nil,percentage_uit_marokko,percentage_uit_marokko.xsi_nil,percentage_niet_westerse_allochtonen,percentage_niet_westerse_allochtonen.xsi_nil,percentage_ongehuwd,percentage_ongehuwd.xsi_nil,percentage_overige_niet_westerse_allochtonen,percentage_overige_niet_westerse_allochtonen.xsi_nil,percentage_uit_suriname,percentage_uit_suriname.xsi_nil,percentage_uit_turkije,percentage_uit_turkije.xsi_nil,percentage_verweduwd,percentage_verweduwd.xsi_nil,percentage_westerse_allochtonen,percentage_westerse_allochtonen.xsi_nil,meest_voorkomende_postcode,meest_voorkomende_postcode.xsi_nil,stedelijkheid_adressen_per_km2,stedelijkheid_adressen_per_km2.xsi_nil,water,water.xsi_nil,wijkcode,wijkcode.xsi_nil,geom,fme_geometry{0},fme_geometry{1}"
    ATTR_ACCUM_MODE = Only Use Result
    COMBINE_GEOM = Use Result
    DATASET = https://geodata.nationaalgeoregister.nl/wijkenbuurten2017/wfs?&request=GetCapabilities&service=WFS
    FEATURETYPES = cbs_buurten_2017
    FORMAT = WFS
    INTERACT = Initiator Contains Result
    OUTPUT_FEATURES_DISPLAY = Schema and Data Features
    WFS_CONNECTION_TIMEOUT = 90
    WFS_DISABLE_AUTOMATIC_READER_TYPE_SELECTION = NO
    WFS_DISABLE_XML_NAMESPACE_PROCESSING = NO
    WFS_ENFORCE_PATH_CONTINUITY_BY = SNAPPING_END_POINTS
    WFS_FLATTEN_XML_FRAGMENTS = NO
    WFS_IGNORE_APPLICATON_SCHEMA = no
    WFS_LOCAL_CACHE_EXPIRY = 60
    WFS_MAP_COMPLEX_PROPERTIES_AS = Nested Attributes
    WFS_MAP_EMBEDDED_OBJECTS_AS = ATTRIBUTES
    WFS_MAP_GEOMETRY_COLUMNS = YES
    WFS_MAP_PREDEFINED_GML_PROPERTIES = NO
    WFS_PREFERRED_VERSION = 1.0.0
    WFS_PREFER_DATASET_URL = No
    WFS_PREFER_POST = No
    WFS_TRANSFER_TIMEOUT = 90
    WFS_USE_OLD_READER = NO
    WFS_USE_SEARCH_ENVELOPE = NO
    WFS_XML_FRAGMENTS_AS_DOCUMENTS = YES
    cbs_buurten_2017 -> AttributeKeeper_3
AttributeKeeper_3
    KEEP_ATTRS = gemeentecode,gemeentenaam,wijkcode,buurtcode,buurtnaam
    -> Oostland_buurten (writer ESRISHAPE_1)
