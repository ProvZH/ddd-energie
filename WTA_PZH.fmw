FME workspace WTA_PZH.fmw
Title: WTA2fgdb
Description: Workspace voor het uitlezen van de gegevens in de 
        Warmtetransitieatlas 
    en exporteren naar een filegeodatabase.
Let op: de lagen die alleen beschikbaar zijn als tiles worden NIET meegenomen. Voorbeelden hiervan zijn: bouwperiodes, gebouwtypes, afgemelde en voorlopige energielabels.

Parameters:
- DestDataset_GEODATABASE_FILE = T:\Databeheer Blauw\Werkplaats\Willy\test.gdb   # File Geodatabase
- SourceDataset_ARCGISFEATURES = https://services5.arcgis.com/PZYGbbhVncO1YI8q/arcgis/rest/services/WTA_PZH_Warmtebronnen/FeatureServer   # Host
- SourceDataset_ARCGISFEATURES_33 = https://services5.arcgis.com/PZYGbbhVncO1YI8q/arcgis/rest/services/restwarmte_potentie_rvo_20160203/FeatureServer   # Host
- SourceDataset_ARCGISFEATURES_25 = https://geoservices.zuid-holland.nl/arcgis/rest/services/Milieu/Milieu_WKO/MapServer   # Host
- SourceDataset_ARCGISFEATURES_41 = https://services5.arcgis.com/PZYGbbhVncO1YI8q/arcgis/rest/services/PZH_WTA_Warmtenetten/FeatureServer   # Host
- SourceDataset_ARCGISFEATURES_29 = https://services5.arcgis.com/PZYGbbhVncO1YI8q/arcgis/rest/services/Gemeentelijk_eigendom/FeatureServer   # Host
- SourceDataset_ARCGISFEATURES_37 = https://services5.arcgis.com/PZYGbbhVncO1YI8q/arcgis/rest/services/bedrijventerreinen_zuidholland/FeatureServer   # Host
- SourceDataset_ARCGISFEATURES_27 = https://services1.arcgis.com/v6W5HAVrpgSg3vts/ArcGIS/rest/services/OuderdomHoofdleidingen_WFL1/FeatureServer   # Host
- SourceDataset_ARCGISFEATURES_45 = https://services5.arcgis.com/PZYGbbhVncO1YI8q/arcgis/rest/services/PZH_WTA_Plancapaciteit2017/FeatureServer   # Host
- SourceDataset_ARCGISFEATURES_35 = https://services5.arcgis.com/PZYGbbhVncO1YI8q/arcgis/rest/services/PZH_WTA_Energieverbruik/FeatureServer   # Host
- SourceDataset_ARCGISFEATURES_39 = https://services5.arcgis.com/PZYGbbhVncO1YI8q/arcgis/rest/services/Glasclusters_warmtevraag_Zuid_Holland/FeatureServer   # Host
- SourceDataset_ARCGISFEATURES_32 = https://services3.arcgis.com/PeOi6aWiQVQNdaI8/ArcGIS/rest/services/KM_Gasvervangingsdata/FeatureServer   # Host
- SourceDataset_ARCGISFEATURES_31 = https://services5.arcgis.com/PZYGbbhVncO1YI8q/arcgis/rest/services/AWZI_CO2_emissie_warmteatlas_20160203/FeatureServer   # Host
- SourceDataset_ARCGISFEATURES_43 = https://services5.arcgis.com/PZYGbbhVncO1YI8q/arcgis/rest/services/PZH_WTA_Kansen_allelectric/FeatureServer   # Host
- SourceDataset_ARCGISFEATURES_34 = https://services5.arcgis.com/PZYGbbhVncO1YI8q/arcgis/rest/services/PZH_WTA_Kansen_warmtenet/FeatureServer   # Host
- SourceDataset_ARCGISFEATURES_36 = https://services5.arcgis.com/PZYGbbhVncO1YI8q/arcgis/rest/services/postcodes_noregret_clip_select_26031/FeatureServer   # Host
- SourceDataset_ARCGISFEATURES_38 = https://services5.arcgis.com/PZYGbbhVncO1YI8q/arcgis/rest/services/PZH_WTA_Potentie_eilanden_metKosten/FeatureServer   # Host
- SourceDataset_ARCGISFEATURES_40 = https://services5.arcgis.com/PZYGbbhVncO1YI8q/arcgis/rest/services/services_grondwaterbescherming_Zuid_Holland/FeatureServer   # Host
- SourceDataset_ARCGISFEATURES_42 = https://services5.arcgis.com/PZYGbbhVncO1YI8q/arcgis/rest/services/WKO_bodempotentie/FeatureServer   # Host

Readers:
- ARCGISFEATURES_1: ARCGISFEATURES from $(SourceDataset_ARCGISFEATURES_33)
- ARCGISFEATURES_2: ARCGISFEATURES from $(SourceDataset_ARCGISFEATURES)
- ARCGISFEATURES_3: ARCGISFEATURES from $(SourceDataset_ARCGISFEATURES_25)
- ARCGISFEATURES_4: ARCGISFEATURES from $(SourceDataset_ARCGISFEATURES_41)
- ARCGISFEATURES_5: ARCGISFEATURES from $(SourceDataset_ARCGISFEATURES_29)
- ARCGISFEATURES_6: ARCGISFEATURES from $(SourceDataset_ARCGISFEATURES_37)
- ARCGISFEATURES_7: ARCGISFEATURES from $(SourceDataset_ARCGISFEATURES_45)
- ARCGISFEATURES_8: ARCGISFEATURES from $(SourceDataset_ARCGISFEATURES_27)
- ARCGISFEATURES_9: ARCGISFEATURES from $(SourceDataset_ARCGISFEATURES_35)
- ARCGISFEATURES_10: ARCGISFEATURES from $(SourceDataset_ARCGISFEATURES_39)
- ARCGISFEATURES_11: ARCGISFEATURES from $(SourceDataset_ARCGISFEATURES_32)
- ARCGISFEATURES_12: ARCGISFEATURES from $(SourceDataset_ARCGISFEATURES_31)
- ARCGISFEATURES_13: ARCGISFEATURES from $(SourceDataset_ARCGISFEATURES_43)
- ARCGISFEATURES_14: ARCGISFEATURES from $(SourceDataset_ARCGISFEATURES_34)
- ARCGISFEATURES_15: ARCGISFEATURES from $(SourceDataset_ARCGISFEATURES_36)
- ARCGISFEATURES_16: ARCGISFEATURES from $(SourceDataset_ARCGISFEATURES_38)
- ARCGISFEATURES_17: ARCGISFEATURES from $(SourceDataset_ARCGISFEATURES_40)
- ARCGISFEATURES_18: ARCGISFEATURES from $(SourceDataset_ARCGISFEATURES_42)

Writers:
- GEODATABASE_FILE_1: GEODATABASE_FILE to $(DestDataset_GEODATABASE_FILE)

CO2_emissie_industrie_warmteatlas_20160203 (reader ARCGISFEATURES_1) [off]
    attributes: OBJECTID esriFieldTypeOID, bedrijf esriFieldTypeString(254), FIRST_sbi_code esriFieldTypeDouble, FIRST_sbi esriFieldTypeString(254), FIRST_doelgroep esriFieldTypeString(254), FIRST_subdoelgr esriFieldTypeString(254), MAX_kgco2_2013 esriFieldTypeDouble, MAX_tj_warmte esriFieldTypeDouble, ORIG_FID esriFieldTypeInteger
    -> CO2_emissies_industrie_2013 (writer GEODATABASE_FILE_1) [off]
Note: Let op: / De eerste drie lagen zijn uitgeschakeld, omdat die al eerder zijn aangeleverd aan de functioneel beheerder van de PI database!
CO2_emissies_industrie_2013 (writer GEODATABASE_FILE_1) [off]
    attributes: OBJECTID integer, bedrijf char(254), FIRST_sbi_code double, FIRST_sbi char(254), FIRST_doelgroep char(254), FIRST_subdoelgr char(254), MAX_kgco2_2013 double, MAX_tj_warmte double, ORIG_FID integer
warmtebronnen_PZH (reader ARCGISFEATURES_2) [off]
    attributes: OBJECTID esriFieldTypeOID, Naam esriFieldTypeString(50), Categorie esriFieldTypeString(50), Brontype esriFieldTypeString(50)
    -> Bestaande_warmtebronnen (writer GEODATABASE_FILE_1) [off]
Bestaande_warmtebronnen (writer GEODATABASE_FILE_1) [off]
    attributes: OBJECTID integer, Naam char(50), Categorie char(50), Brontype char(50)
Vergunningen warmte-koudeopslag tot en met 1 juli 2017 (reader ARCGISFEATURES_3) [off]
    attributes: OBJECTID esriFieldTypeOID, X_coordinaat esriFieldTypeDouble, Y_coordinaat esriFieldTypeDouble, Locatie esriFieldTypeString(255), Straat esriFieldTypeString(255), Plaats esriFieldTypeString(255), Besluitnr esriFieldTypeString(255), Vergund_m3_h esriFieldTypeDouble, Vergund_m3_jaar esriFieldTypeDouble, WVP esriFieldTypeString(255), LGR_inr_nr esriFieldTypeDouble, Datum_besluit esriFieldTypeDate
    -> Vergunde_WKO_systemen_2017 (writer GEODATABASE_FILE_1) [off]
Vergunde_WKO_systemen_2017 (writer GEODATABASE_FILE_1) [off]
    attributes: OBJECTID integer, X_coordinaat double, Y_coordinaat double, Locatie char(255), Straat char(255), Plaats char(255), Besluitnr char(255), Vergund_m3_h double, Vergund_m3_jaar double, WVP char(255), LGR_inr_nr double, Datum_besluit date
warmtenetten_merge (reader ARCGISFEATURES_4)
    attributes: OBJECTID esriFieldTypeOID, Netbeheerder esriFieldTypeString(255), Nettype esriFieldTypeString(255), Warmterotonde esriFieldTypeString(255), Status esriFieldTypeString(255), Netnaam esriFieldTypeString(255), Bronnen esriFieldTypeString(255), Shape__Length esriFieldTypeDouble
    -> Warmtenetten (writer GEODATABASE_FILE_1)
Warmtenetten (writer GEODATABASE_FILE_1)
    attributes: OBJECTID integer, Netbeheerder char(255), Nettype char(255), Warmterotonde char(255), Status char(255), Netnaam char(255), Bronnen char(255), Shape__Length double
Gemeentelijk_eigendom (reader ARCGISFEATURES_5)
    attributes: OBJECTID esriFieldTypeOID, GEMEENTENAAM esriFieldTypeString(100), VBO_ID esriFieldTypeString(64), PHT esriFieldTypeString(72), NAAM esriFieldTypeString(1024), PAND_ID esriFieldTypeString(64), GEBRUIKSDOEL esriFieldTypeString(320), VBO_OPPERVLAKTE esriFieldTypeDouble, STATUS_ADRES esriFieldTypeString(400), IND_MEERDERE_GERECHTIGDEN esriFieldTypeString(1)
    -> Gemeentevastgoed (writer GEODATABASE_FILE_1)
Gemeentevastgoed (writer GEODATABASE_FILE_1)
    attributes: OBJECTID integer, GEMEENTENAAM char(100), VBO_ID char(64), PHT char(72), NAAM char(1024), PAND_ID char(64), GEBRUIKSDOEL char(320), VBO_OPPERVLAKTE double, STATUS_ADRES char(400), IND_MEERDERE_GERECHTIGDEN char(1)
werklocaties_zuidholland (reader ARCGISFEATURES_6)
    attributes: OBJECTID esriFieldTypeOID, RINNUMMER esriFieldTypeInteger, NAAM esriFieldTypeString(255), STATUS esriFieldTypeString(255), GEMEENTE esriFieldTypeString(255), PLAATS esriFieldTypeString(255), TYPE_ esriFieldTypeString(255), AANBOD_JN esriFieldTypeString(255), AANBOD esriFieldTypeDouble, DIRECT esriFieldTypeDouble, BRUTO_OPPVL esriFieldTypeDouble, NETTO_OPPVL esriFieldTypeDouble, UITGEGEVEN esriFieldTypeDouble, MIN_PRIJS esriFieldTypeDouble, MAX_PRIJS esriFieldTypeDouble, BOUWHOOGTE esriFieldTypeDouble, BOUWPERC esriFieldTypeDouble, HINDERCAT esriFieldTypeDouble, HAVEN esriFieldTypeString(255), LOSKADE esriFieldTypeString(255), LOSK_MOGEL esriFieldTypeString(255), VAARWATER esriFieldTypeString(255), SPOOR esriFieldTypeString(255), WEG esriFieldTypeString(255), SCHIPHOL esriFieldTypeDouble, ZESTIENH esriFieldTypeDouble, DATUM esriFieldTypeString(255), BEDRIJVEN esriFieldTypeDouble, ARBPL esriFieldTypeDouble, KONTAKTPER esriFieldTypeString(255),
      TELEFOON esriFieldTypeString(255), EMAIL esriFieldTypeString(255), A_INRICHT esriFieldTypeString(255), GELUIDSZONE esriFieldTypeDouble, BESTPLAN esriFieldTypeSmallInteger, GlobalID esriFieldTypeString(40)
    -> Bedrijventerreinen (writer GEODATABASE_FILE_1)
Bedrijventerreinen (writer GEODATABASE_FILE_1)
    attributes: OBJECTID integer, RINNUMMER integer, NAAM char(255), STATUS char(255), GEMEENTE char(255), PLAATS char(255), TYPE_ char(255), AANBOD_JN char(255), AANBOD double, DIRECT double, BRUTO_OPPVL double, NETTO_OPPVL double, UITGEGEVEN double, MIN_PRIJS double, MAX_PRIJS double, BOUWHOOGTE double, BOUWPERC double, HINDERCAT double, HAVEN char(255), LOSKADE char(255), LOSK_MOGEL char(255), VAARWATER char(255), SPOOR char(255), WEG char(255), SCHIPHOL double, ZESTIENH double, DATUM char(255), BEDRIJVEN double, ARBPL double, KONTAKTPER char(255),
      TELEFOON char(255), EMAIL char(255), A_INRICHT char(255), GELUIDSZONE double, BESTPLAN smallint, GlobalID char(40)
plancapaciteit_woonvisie20171 (reader ARCGISFEATURES_7)
    attributes: OBJECTID esriFieldTypeOID, BU_CODE esriFieldTypeString(10), SUM__17_24Dir esriFieldTypeDouble, SUM__17_24Res esriFieldTypeDouble, SUM__17_24BA esriFieldTypeDouble, SUM__25_29Dir esriFieldTypeDouble, SUM__25_29Res esriFieldTypeDouble, SUM__25_29BA esriFieldTypeDouble, SUM__30_34Dir esriFieldTypeDouble, SUM__30_34Res esriFieldTypeDouble, SUM__35_39Dir esriFieldTypeDouble, SUM__35_39Res esriFieldTypeDouble, SUM__2030_2034 esriFieldTypeDouble, SUM__2035_2039 esriFieldTypeDouble, Subregio esriFieldTypeString(254), Regio esriFieldTypeString(254), Gemeente esriFieldTypeString(254), CBScode esriFieldTypeString(254), BU_NAAM esriFieldTypeString(60), Zuidvleuge esriFieldTypeString(254), BSD esriFieldTypeString(254), ABF5 esriFieldTypeString(254), ABF3 esriFieldTypeString(254), TotaalSaldo esriFieldTypeInteger, Shape__Area esriFieldTypeDouble, Shape__Length esriFieldTypeDouble
    -> Plancapaciteit_2017 (writer GEODATABASE_FILE_1)
Note: Let op: / Ouderdom_gasleidingen_Liander en Ouderdom_gasleidingen_Steden zijn hele grote datasets! Alleen importeren als het nodig is.
Plancapaciteit_2017 (writer GEODATABASE_FILE_1)
    attributes: OBJECTID integer, BU_CODE char(10), SUM__17_24Dir double, SUM__17_24Res double, SUM__17_24BA double, SUM__25_29Dir double, SUM__25_29Res double, SUM__25_29BA double, SUM__30_34Dir double, SUM__30_34Res double, SUM__35_39Dir double, SUM__35_39Res double, SUM__2030_2034 double, SUM__2035_2039 double, Subregio char(254), Regio char(254), Gemeente char(254), CBScode char(254), BU_NAAM char(60), Zuidvleuge char(254), BSD char(254), ABF5 char(254), ABF3 char(254), TotaalSaldo integer, Shape__Area double, Shape__Length double
OMT_BAG_PAND_DISTRLDG_OUDERDOM (reader ARCGISFEATURES_8) [off]
    attributes: OBJECTID_1 esriFieldTypeOID, OBJECTID esriFieldTypeDouble, PAND_ID esriFieldTypeInteger, POSTCODE esriFieldTypeString(6), GEWOGEN_GEMIDDELDE_CATEGORIE esriFieldTypeDouble, Shape__Area esriFieldTypeDouble, Shape__Length esriFieldTypeDouble
    -> Ouderdom_gasleidingen_Liander (writer GEODATABASE_FILE_1) [off]
Ouderdom_gasleidingen_Liander (writer GEODATABASE_FILE_1) [off]
    attributes: OBJECTID_1 integer, OBJECTID double, PAND_ID integer, POSTCODE char(6), GEWOGEN_GEMIDDELDE_CATEGORIE double, Shape__Area double, Shape__Length double
Gasvervangingsdata (reader ARCGISFEATURES_11) [off]
    attributes: OBJECTID esriFieldTypeOID, Status esriFieldTypeString(254), Shape__Length esriFieldTypeDouble
    -> Ouderdom_gasleidingen_Stedin (writer GEODATABASE_FILE_1) [off]
Ouderdom_gasleidingen_Stedin (writer GEODATABASE_FILE_1) [off]
    attributes: OBJECTID integer, Status char(254), Shape__Length double
Energieverbruik_CBS2014_PC6Woon (reader ARCGISFEATURES_9)
    attributes: OBJECTID esriFieldTypeOID, Postcode esriFieldTypeString(6), G_W_GEM esriFieldTypeDouble, G_W_SOM esriFieldTypeDouble, G_W_N esriFieldTypeDouble, E_W_GEM esriFieldTypeDouble, E_W_SOM esriFieldTypeDouble, E_W_N esriFieldTypeDouble, Shape__Area esriFieldTypeDouble, Shape__Length esriFieldTypeDouble
    -> Particulier_energieverbruik_CBS_2014_PC6 (writer GEODATABASE_FILE_1)
Particulier_energieverbruik_CBS_2014_PC6 (writer GEODATABASE_FILE_1)
    attributes: OBJECTID integer, Postcode char(6), G_W_GEM double, G_W_SOM double, G_W_N double, E_W_GEM double, E_W_SOM double, E_W_N double, Shape__Area double, Shape__Length double
Energieverbruik_CBS2014_Buurt (reader ARCGISFEATURES_9)
    attributes: OBJECTID esriFieldTypeOID, Join_Count esriFieldTypeInteger, BU_CODE esriFieldTypeString(10), BU_NAAM esriFieldTypeString(60), WK_CODE esriFieldTypeString(8), GM_CODE esriFieldTypeString(6), GM_NAAM esriFieldTypeString(60), G_W_gem esriFieldTypeDouble, G_W_som esriFieldTypeDouble, G_W_N esriFieldTypeDouble, E_W_gem esriFieldTypeDouble, E_W_som esriFieldTypeDouble, E_W_N esriFieldTypeDouble, G_B_gem esriFieldTypeDouble, G_B_som esriFieldTypeDouble, G_B_N esriFieldTypeDouble, E_B_gem esriFieldTypeDouble, E_B_som esriFieldTypeDouble, E_B_N esriFieldTypeDouble, Opp_ha esriFieldTypeDouble, Provincienaam esriFieldTypeString(28), Shape__Area esriFieldTypeDouble, Shape__Length esriFieldTypeDouble
    -> Energieverbruik_CBS_2014_buurt (writer GEODATABASE_FILE_1)
Energieverbruik_CBS_2014_buurt (writer GEODATABASE_FILE_1)
    attributes: OBJECTID integer, Join_Count integer, BU_CODE char(10), BU_NAAM char(60), WK_CODE char(8), GM_CODE char(6), GM_NAAM char(60), G_W_gem double, G_W_som double, G_W_N double, E_W_gem double, E_W_som double, E_W_N double, G_B_gem double, G_B_som double, G_B_N double, E_B_gem double, E_B_som double, E_B_N double, Opp_ha double, Provincienaam char(28), Shape__Area double, Shape__Length double
Energieverbruik_CBS2014_PC6Bedrijf (reader ARCGISFEATURES_9)
    attributes: OBJECTID esriFieldTypeOID, Postcode esriFieldTypeString(6), G_B_GEM esriFieldTypeDouble, G_B_SOM esriFieldTypeDouble, G_B_N esriFieldTypeDouble, E_B_GEM esriFieldTypeDouble, E_B_SOM esriFieldTypeDouble, E_B_N esriFieldTypeDouble, G_B_SOM_TJ esriFieldTypeDouble, G_B_GEM_GJ esriFieldTypeDouble, G_B_GEM_M2 esriFieldTypeInteger, Shape__Area esriFieldTypeDouble, Shape__Length esriFieldTypeDouble
    -> Zakelijk_energieverbruik_CSB_2014_PC6 (writer GEODATABASE_FILE_1)
Zakelijk_energieverbruik_CSB_2014_PC6 (writer GEODATABASE_FILE_1)
    attributes: OBJECTID integer, Postcode char(6), G_B_GEM double, G_B_SOM double, G_B_N double, E_B_GEM double, E_B_SOM double, E_B_N double, G_B_SOM_TJ double, G_B_GEM_GJ double, G_B_GEM_M2 integer, Shape__Area double, Shape__Length double
glasclusters_zuidholland (reader ARCGISFEATURES_10)
    attributes: OBJECTID esriFieldTypeOID, aantal_BAG_glastuinbouwbedrijve esriFieldTypeSmallInteger, areaal_ha_gedocumenteerd esriFieldTypeDouble, warmtevraag_PJ esriFieldTypeDouble, warmtebehoefte_in_basislast_MW esriFieldTypeDouble, CO2_behoefte_ton_per_jaar esriFieldTypeDouble, Clustergebied esriFieldTypeString(50), Cluster esriFieldTypeString(50)
    -> Glasclusters_warmtevraag (writer GEODATABASE_FILE_1)
Glasclusters_warmtevraag (writer GEODATABASE_FILE_1)
    attributes: OBJECTID integer, aantal_BAG_glastuinbouwbedrijve smallint, areaal_ha_gedocumenteerd double, warmtevraag_PJ double, warmtebehoefte_in_basislast_MW double, CO2_behoefte_ton_per_jaar double, Clustergebied char(50), Cluster char(50)
Afvalwaterzuiveringsinstallaties (reader ARCGISFEATURES_12)
    attributes: OBJECTID esriFieldTypeOID, bedrijf esriFieldTypeString(254), FIRST_sbi_code esriFieldTypeDouble, FIRST_sbi esriFieldTypeString(254), FIRST_doelgroep esriFieldTypeString(254), FIRST_subdoelgr esriFieldTypeString(254), MAX_kgco2_2013 esriFieldTypeDouble, MAX_tj_warmte esriFieldTypeDouble, ORIG_FID esriFieldTypeInteger
    -> Afvalwaterzuiveringsinstallaties (writer GEODATABASE_FILE_1)
Afvalwaterzuiveringsinstallaties (writer GEODATABASE_FILE_1)
    attributes: OBJECTID integer, bedrijf char(254), FIRST_sbi_code double, FIRST_sbi char(254), FIRST_doelgroep char(254), FIRST_subdoelgr char(254), MAX_kgco2_2013 double, MAX_tj_warmte double, ORIG_FID integer
Panden_Center_AE_2603 (reader ARCGISFEATURES_13)
    attributes: OBJECTID esriFieldTypeOID, XCoord esriFieldTypeDouble, YCoord esriFieldTypeDouble, Identificatie esriFieldTypeString(255), Bouwjaar esriFieldTypeInteger, Opp_taal esriFieldTypeInteger, Gebruiksfunctie esriFieldTypeString(255), Pandtype esriFieldTypeString(255), pand_epi esriFieldTypeDouble, pand_labelCombi esriFieldTypeString(255), SJV_gas_m3_PC6_min esriFieldTypeInteger, Indicatie_Blokverwarming esriFieldTypeString(255), Corporatiebezit esriFieldTypeString(1024), Count_wocowoningen esriFieldTypeString(1024), Kanscat_HT_warmtenet esriFieldTypeString(100), Kanscat_AllElectric esriFieldTypeString(100), Kanscat_HT_warmtenet_WEQ esriFieldTypeInteger, Kanscat_AllElectric_WEQ esriFieldTypeInteger
    -> Kansrijke_panden_voor_all_electric (writer GEODATABASE_FILE_1)
Kansrijke_panden_voor_all_electric (writer GEODATABASE_FILE_1)
    attributes: OBJECTID integer, XCoord double, YCoord double, Identificatie char(255), Bouwjaar integer, Opp_taal integer, Gebruiksfunctie char(255), Pandtype char(255), pand_epi double, pand_labelCombi char(255), SJV_gas_m3_PC6_min integer, Indicatie_Blokverwarming char(255), Corporatiebezit char(1024), Count_wocowoningen char(1024), Kanscat_HT_warmtenet char(100), Kanscat_AllElectric char(100), Kanscat_HT_warmtenet_WEQ integer, Kanscat_AllElectric_WEQ integer
Panden_Center_HT_2603 (reader ARCGISFEATURES_14)
    attributes: OBJECTID esriFieldTypeOID, XCoord esriFieldTypeDouble, YCoord esriFieldTypeDouble, Identificatie esriFieldTypeString(255), Bouwjaar esriFieldTypeInteger, Opp_taal esriFieldTypeInteger, Gebruiksfunctie esriFieldTypeString(255), Pandtype esriFieldTypeString(255), pand_epi esriFieldTypeDouble, pand_labelCombi esriFieldTypeString(255), SJV_gas_m3_PC6_min esriFieldTypeInteger, Indicatie_Blokverwarming esriFieldTypeString(255), Corporatiebezit esriFieldTypeString(1024), Count_wocowoningen esriFieldTypeString(1024), Kanscat_HT_warmtenet esriFieldTypeString(100), Kanscat_AllElectric esriFieldTypeString(100), Kanscat_HT_warmtenet_WEQ esriFieldTypeInteger, Kanscat_AllElectric_WEQ esriFieldTypeInteger
    -> Kansrijke_panden_voor_warmtenet (writer GEODATABASE_FILE_1)
Kansrijke_panden_voor_warmtenet (writer GEODATABASE_FILE_1)
    attributes: OBJECTID integer, XCoord double, YCoord double, Identificatie char(255), Bouwjaar integer, Opp_taal integer, Gebruiksfunctie char(255), Pandtype char(255), pand_epi double, pand_labelCombi char(255), SJV_gas_m3_PC6_min integer, Indicatie_Blokverwarming char(255), Corporatiebezit char(1024), Count_wocowoningen char(1024), Kanscat_HT_warmtenet char(100), Kanscat_AllElectric char(100), Kanscat_HT_warmtenet_WEQ integer, Kanscat_AllElectric_WEQ integer
postcodes_noregret_clip_select_26031 (reader ARCGISFEATURES_15)
    attributes: OBJECTID esriFieldTypeOID, woon_count esriFieldTypeInteger, Inv_deg70_eur_pnd_v esriFieldTypeInteger, Inv_deg70_eur_pnd_t esriFieldTypeInteger, Gv_norm_m3_pnd esriFieldTypeInteger, Besp_deg70_GJ_pnd_v esriFieldTypeDouble, Besp_deg70_GJ_pnd_t esriFieldTypeDouble, Ort_deg70_eur_pnd_v esriFieldTypeInteger, Ort_deg70_eur_pnd_t esriFieldTypeInteger, Postcode esriFieldTypeString(6), INW_014 esriFieldTypeInteger, INW_1524 esriFieldTypeInteger, INW_2544 esriFieldTypeInteger, INW_4564 esriFieldTypeInteger, INW_65PL esriFieldTypeInteger, P_HUURWON esriFieldTypeInteger, P_KOOPWON esriFieldTypeInteger, WON_HCORP esriFieldTypeInteger, M_INKHH esriFieldTypeString(8000), UITKMINAOW esriFieldTypeInteger, Inv_deg70_eur_pnd_gem esriFieldTypeInteger, Inv_deg70_eur_pnd_str esriFieldTypeString(255), Ort_deg70_eur_pnd_gem esriFieldTypeInteger, Ort_deg70_eur_pnd_str esriFieldTypeString(255), Besp_deg70_GJ_pnd_gem esriFieldTypeDouble, Besp_deg70_GJ_pnd_str esriFieldTypeString(255), Kanscategorie_noregret esriFieldTypeString(100), Shape__Area esriFieldTypeDouble, Shape__Length esriFieldTypeDouble
    -> Kansrijke_postcodes_voor_no_regret_maatregelen (writer GEODATABASE_FILE_1)
Kansrijke_postcodes_voor_no_regret_maatregelen (writer GEODATABASE_FILE_1)
    attributes: OBJECTID integer, woon_count integer, Inv_deg70_eur_pnd_v integer, Inv_deg70_eur_pnd_t integer, Gv_norm_m3_pnd integer, Besp_deg70_GJ_pnd_v double, Besp_deg70_GJ_pnd_t double, Ort_deg70_eur_pnd_v integer, Ort_deg70_eur_pnd_t integer, Postcode char(6), INW_014 integer, INW_1524 integer, INW_2544 integer, INW_4564 integer, INW_65PL integer, P_HUURWON integer, P_KOOPWON integer, WON_HCORP integer, M_INKHH char(8000), UITKMINAOW integer, Inv_deg70_eur_pnd_gem integer, Inv_deg70_eur_pnd_str char(255), Ort_deg70_eur_pnd_gem integer, Ort_deg70_eur_pnd_str char(255), Besp_deg70_GJ_pnd_gem double, Besp_deg70_GJ_pnd_str char(255), Kanscategorie_noregret char(100), Shape__Area double, Shape__Length double
Potentie_eiland_allelectric (reader ARCGISFEATURES_16)
    attributes: OBJECTID esriFieldTypeOID, Join_Count esriFieldTypeInteger, TARGET_FID esriFieldTypeInteger, Inv_deg55_eur_pnd_v esriFieldTypeInteger, Inv_deg55_eur_pnd_t esriFieldTypeInteger, Ort_deg55_eur_pnd_v esriFieldTypeInteger, Ort_deg55_eur_pnd_t esriFieldTypeInteger, Inv_ae_eur_pnd_v esriFieldTypeInteger, Inv_ae_eur_pnd_t esriFieldTypeInteger, Inv_t_ae_eur_pnd_v esriFieldTypeInteger, Inv_t_ae_eur_pnd_t esriFieldTypeInteger, Ort_t_ae_eur_pnd_v esriFieldTypeInteger, Ort_t_ae_eur_pnd_t esriFieldTypeInteger, Woningequivalenten esriFieldTypeInteger, woon_count esriFieldTypeInteger, Count_wocowoningen esriFieldTypeInteger, Kanscat_AllElectric_WEQ esriFieldTypeInteger, Inv_deg55_eur_won_str esriFieldTypeString(255), Ort_deg55_eur_won_str esriFieldTypeString(255), Inv_ae_eur_won_str esriFieldTypeString(255), Inv_t_ae_eur_won_str esriFieldTypeString(255), Ort_t_ae_eur_won_str esriFieldTypeString(255), Shape__Area esriFieldTypeDouble, Shape__Length esriFieldTypeDouble
    -> Potentie_eiland_all_electric (writer GEODATABASE_FILE_1)
Potentie_eiland_all_electric (writer GEODATABASE_FILE_1)
    attributes: OBJECTID integer, Join_Count integer, TARGET_FID integer, Inv_deg55_eur_pnd_v integer, Inv_deg55_eur_pnd_t integer, Ort_deg55_eur_pnd_v integer, Ort_deg55_eur_pnd_t integer, Inv_ae_eur_pnd_v integer, Inv_ae_eur_pnd_t integer, Inv_t_ae_eur_pnd_v integer, Inv_t_ae_eur_pnd_t integer, Ort_t_ae_eur_pnd_v integer, Ort_t_ae_eur_pnd_t integer, Woningequivalenten integer, woon_count integer, Count_wocowoningen integer, Kanscat_AllElectric_WEQ integer, Inv_deg55_eur_won_str char(255), Ort_deg55_eur_won_str char(255), Inv_ae_eur_won_str char(255), Inv_t_ae_eur_won_str char(255), Ort_t_ae_eur_won_str char(255), Shape__Area double, Shape__Length double
Potentie_eiland_warmtenet (reader ARCGISFEATURES_16)
    attributes: OBJECTID esriFieldTypeOID, Join_Count esriFieldTypeInteger, TARGET_FID esriFieldTypeInteger, Woningequivalenten esriFieldTypeInteger, Inv_deg70_eur_pnd_v esriFieldTypeInteger, Inv_deg70_eur_pnd_t esriFieldTypeInteger, Ort_deg70_eur_pnd_v esriFieldTypeInteger, Ort_deg70_eur_pnd_t esriFieldTypeInteger, Inv_warmte_eur_pnd_v esriFieldTypeInteger, Inv_warmte_eur_pnd_t esriFieldTypeInteger, Inv_t_warmte_eur_pnd_v esriFieldTypeInteger, Inv_t_warmte_eur_pnd_t esriFieldTypeInteger, Ort_t_warmte_eur_pnd_v esriFieldTypeInteger, Ort_t_warmte_eur_pnd_t esriFieldTypeInteger, woon_count esriFieldTypeInteger, Count_wocowoningen esriFieldTypeInteger, Kanscat_HT_warmtenet_WEQ esriFieldTypeInteger, Inv_deg70_eur_won_str esriFieldTypeString(255), Ort_deg70_eur_won_str esriFieldTypeString(255), Inv_warmte_eur_won_str esriFieldTypeString(255), Inv_t_warmte_eur_won_str esriFieldTypeString(255), Ort_t_warmte_eur_won_str esriFieldTypeString(255), Shape__Area esriFieldTypeDouble, Shape__Length esriFieldTypeDouble
    -> Potentie_eiland_warmtenet (writer GEODATABASE_FILE_1)
Potentie_eiland_warmtenet (writer GEODATABASE_FILE_1)
    attributes: OBJECTID integer, Join_Count integer, TARGET_FID integer, Woningequivalenten integer, Inv_deg70_eur_pnd_v integer, Inv_deg70_eur_pnd_t integer, Ort_deg70_eur_pnd_v integer, Ort_deg70_eur_pnd_t integer, Inv_warmte_eur_pnd_v integer, Inv_warmte_eur_pnd_t integer, Inv_t_warmte_eur_pnd_v integer, Inv_t_warmte_eur_pnd_t integer, Ort_t_warmte_eur_pnd_v integer, Ort_t_warmte_eur_pnd_t integer, woon_count integer, Count_wocowoningen integer, Kanscat_HT_warmtenet_WEQ integer, Inv_deg70_eur_won_str char(255), Ort_deg70_eur_won_str char(255), Inv_warmte_eur_won_str char(255), Inv_t_warmte_eur_won_str char(255), Ort_t_warmte_eur_won_str char(255), Shape__Area double, Shape__Length double
Grondwaterbescherming Zuid-Holland (reader ARCGISFEATURES_17)
    attributes: OBJECTID_1 esriFieldTypeOID, gml_parent_id esriFieldTypeString(254), gml_id esriFieldTypeString(254), OBJECTID esriFieldTypeInteger, OMSCHRIJVI esriFieldTypeString(30), TYPE esriFieldTypeInteger, KAARTNAAM esriFieldTypeString(40), DATUM_GELD esriFieldTypeString(16), GlobalID esriFieldTypeString(254), DATUM esriFieldTypeString(10)
    -> Grondwaterbescherming (writer GEODATABASE_FILE_1)
Grondwaterbescherming (writer GEODATABASE_FILE_1)
    attributes: OBJECTID_1 integer, gml_parent_id char(254), gml_id char(254), OBJECTID integer, OMSCHRIJVI char(30), TYPE integer, KAARTNAAM char(40), DATUM_GELD char(16), GlobalID char(254), DATUM char(10)
WKO - Potentie eerste watervoerende pakket (reader ARCGISFEATURES_18)
    attributes: OBJECTID_1 esriFieldTypeOID, gml_parent_id esriFieldTypeString(254), gml_id esriFieldTypeString(254), OBJECTID esriFieldTypeInteger, GRIDCODE esriFieldTypeDouble, BESCHRIJVI esriFieldTypeString(254), GlobalID esriFieldTypeString(254)
    -> WKO_potentie_eerste_watervoerende_pakket (writer GEODATABASE_FILE_1)
WKO_potentie_eerste_watervoerende_pakket (writer GEODATABASE_FILE_1)
    attributes: OBJECTID_1 integer, gml_parent_id char(254), gml_id char(254), OBJECTID integer, GRIDCODE double, BESCHRIJVI char(254), GlobalID char(254)
WKO - Potentie tweede en derde watervoerende pakket (reader ARCGISFEATURES_18)
    attributes: OBJECTID_1 esriFieldTypeOID, gml_parent_id esriFieldTypeString(254), gml_id esriFieldTypeString(254), OBJECTID esriFieldTypeInteger, GRIDCODE esriFieldTypeDouble, OMSCHRIJVI esriFieldTypeString(254), GlobalID esriFieldTypeString(254)
    -> WKO_potentie_tweede_en_derde_watervoerende_pakket (writer GEODATABASE_FILE_1)
WKO_potentie_tweede_en_derde_watervoerende_pakket (writer GEODATABASE_FILE_1)
    attributes: OBJECTID_1 integer, gml_parent_id char(254), gml_id char(254), OBJECTID integer, GRIDCODE double, OMSCHRIJVI char(254), GlobalID char(254)
