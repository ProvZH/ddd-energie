FME workspace hoogspanningsnet.com2dataloket.fmw
Title: Hoogspanningsnet.com2Dataloket
Description: Workspace om de gegevens uit https://webkaart.hoogspanningsnet.com weg te uploaden naar het Dataloket van de provincie Zuid-Holland.
Soms geeft de workspace een error. De website geeft de HTTPCaller een HTTP error 507 of 503 terug. De website is dan overbelast. Probeer het later nog een keer.
History: ,7-2-2019,Willy Tadema,

Parameters:
- token =   # Token
- SourceDataset_WFS = https://geodata.nationaalgeoregister.nl/bestuurlijkegrenzen/wfs?   # Source WFS (Web Feature Service) URL

Readers:
- WFS_1: WFS from $(SourceDataset_WFS)

Note: Soms geeft de workspace een error. / De website geeft de HTTPCaller een HTTP error 507 of 503 terug. / De website is dan overbelast. Probeer het later nog een keer.
provincies (reader WFS_1)
    attributes: gml_parent_id xml_buffer, gml_parent_property xml_buffer, gml_id xml_buffer, gid xml_int32, gid.xsi_nil xml_boolean, provincienaam xml_buffer, provincienaam.xsi_nil xml_boolean, geom xml_geometry
    -> Reprojector
Reprojector
    DEST = EPSG:4326
    INTERPOLATION_TYPE_NAME = Nearest Neighbor
    RASTER_CELL_SIZE = Preserve Cells
    RASTER_TOLERANCE = 0.0
    SOURCE = Read from feature
    REPROJECTED -> BoundsExtractor
BoundsExtractor
    XMAX = x_max
    XMIN = x_min
    YMAX = y_max
    YMIN = y_min
    -> Junction
Junction
    -> HoogspanningsnetQuerier [Query_parameters]
    -> HoogspanningsnetQuerier_2 [Query_parameters]
    -> HoogspanningsnetQuerier_3 [Query_parameters]
    -> HoogspanningsnetQuerier_4 [Query_parameters]
    -> HoogspanningsnetQuerier_5 [Query_parameters]
Note: Masten
HoogspanningsnetQuerier
    LAYER = mast
    X_MAX = @Value(x_max)
    X_MIN = @Value(x_min)
    Y_MAX = @Value(y_max)
    Y_MIN = @Value(y_min)
    Results -> AttributeExposer
AttributeExposer
    ATTR_LIST = Beheerder,Benutting,Bouwwijze,Hoofdtype,In_dienst,Land,Mastfunctie,Masthoogte,Mastmodel,Mastnummer,Naam,Spanning,Subtype,Verbinding,Opmerkingen,Foto,Circuits
    -> DataloketUploader [Parameters]
DataloketUploader
    CONTACTPERSOON = Rogier Pronk
    OMSCHRIJVING = Masten van Hoogspanningsnet.com gedownload op 7-2-2019. Licentie is CC-BY-NC-ND.
    TAGS = energievoorziening, infrastructuur
    THEMAS = Energie
    TITEL = Masten uit de HoogspanningsNet Netkaart.
    TOEGANG = Openbaar
    TYPE = Dataset
    token = Bearer $(token)
    -> HTTPCaller_Output
    <Rejected> -> HTTPCaller__Rejected_
HTTPCaller_Output: Inspector
HTTPCaller__Rejected_: Inspector
Note: Terreinen
HoogspanningsnetQuerier_2
    LAYER = terr
    X_MAX = @Value(x_max)
    X_MIN = @Value(x_min)
    Y_MAX = @Value(y_max)
    Y_MIN = @Value(y_min)
    Results -> AttributeExposer_2
AttributeExposer_2
    ATTR_LIST = Aantal_velden,Bedrijfsspanning,Beheerder,Beheerdercode,Beheerdernaam,Constructiewijze,Frequentie,Hoofdtype,Hoogste_spanning,In_dienst,Land,Naam,Railcapaciteit,Railconfiguratie,Spanning,Systeem,Opmerkingen,Foto
    -> DataloketUploader_2 [Parameters]
DataloketUploader_2
    CONTACTPERSOON = Rogier Pronk
    OMSCHRIJVING = Terreinen van Hoogspanningsnet.com gedownload op 7-2-2019. Licentie is CC-BY-NC-ND.
    TAGS = energievoorziening, infrastructuur
    THEMAS = Energie
    TITEL = Terreinen uit de HoogspanningsNet Netkaart.
    TOEGANG = Openbaar
    TYPE = Dataset
    token = Bearer $(token)
    -> HTTPCaller_Output_2
    <Rejected> -> HTTPCaller__Rejected__2
HTTPCaller_Output_2: Inspector
HTTPCaller__Rejected__2: Inspector
Note: Knooppunten
HoogspanningsnetQuerier_3
    LAYER = knpp
    X_MAX = @Value(x_max)
    X_MIN = @Value(x_min)
    Y_MAX = @Value(y_max)
    Y_MIN = @Value(y_min)
    Results -> AttributeExposer_3
AttributeExposer_3
    ATTR_LIST = Beheerder,IconPNG,In_dienst,Land,Naam,Netsituatie,Spanning,Opmerkingen,Foto
    -> AttributeManager
AttributeManager
    ATTR_TABLE:
      REMOVE Hoofdtype
      SET_TO IconPNG = https://webkaart.hoogspanningsnet.com/files/@Value(IconPNG)
    -> DataloketUploader_3 [Parameters]
DataloketUploader_3
    CONTACTPERSOON = Rogier Pronk
    OMSCHRIJVING = Knooppunten van Hoogspanningsnet.com gedownload op 7-2-2019. Licentie is CC-BY-NC-ND.
    TAGS = energievoorziening, infrastructuur
    THEMAS = Energie
    TITEL = Knooppunten uit de HoogspanningsNet Netkaart.
    TOEGANG = Openbaar
    TYPE = Dataset
    token = Bearer $(token)
    -> HTTPCaller_Output_3
    <Rejected> -> HTTPCaller__Rejected__3
HTTPCaller_Output_3: Inspector
HTTPCaller__Rejected__3: Inspector
Note: Verbindingen
HoogspanningsnetQuerier_4
    LAYER = verb
    X_MAX = @Value(x_max)
    X_MIN = @Value(x_min)
    Y_MAX = @Value(y_max)
    Y_MIN = @Value(y_min)
    Results -> AttributeExposer_4
AttributeExposer_4
    ATTR_LIST = Bedrijfsspanning,Beheerder,Beheerdercode,Beheerdernummer,Constructiewijze,Deelnet,Frequentie,Hoofdtype,Hoogste_spanning,In_dienst,Land,Lengte,Naam,Spanning,Systeem,Transportcapaciteit,Opmerkingen,Foto
    -> DataloketUploader_4 [Parameters]
DataloketUploader_4
    CONTACTPERSOON = Rogier Pronk
    OMSCHRIJVING = Verbindingen van Hoogspanningsnet.com gedownload op 7-2-2019. Licentie is CC-BY-NC-ND.
    TAGS = energievoorziening, infrastructuur
    THEMAS = Energie
    TITEL = Verbindingen uit de HoogspanningsNet Netkaart.
    TOEGANG = Openbaar
    TYPE = Dataset
    token = Bearer $(token)
    -> HTTPCaller_Output_4
    <Rejected> -> HTTPCaller__Rejected__4
HTTPCaller_Output_4: Inspector
HTTPCaller__Rejected__4: Inspector
Note: Stations
HoogspanningsnetQuerier_5
    LAYER = stat
    X_MAX = @Value(x_max)
    X_MIN = @Value(x_min)
    Y_MAX = @Value(y_max)
    Y_MIN = @Value(y_min)
    Results -> AttributeExposer_5
AttributeExposer_5
    ATTR_LIST = Afkorting,Beheerder_primair,Beheerder_secundair,Hoofdtype,In_dienst,Land,Naam,Spanning,Spanningen,Type,Opmerkingen,Foto
    -> DataloketUploader_5 [Parameters]
DataloketUploader_5
    CONTACTPERSOON = Rogier Pronk
    OMSCHRIJVING = Stations van Hoogspanningsnet.com gedownload op 7-2-2019. Licentie is CC-BY-NC-ND.
    TAGS = energievoorziening, infrastructuur
    THEMAS = Energie
    TITEL = Stations uit de HoogspanningsNet Netkaart.
    TOEGANG = Openbaar
    TYPE = Dataset
    token = Bearer $(token)
    -> HTTPCaller_Output_5
    <Rejected> -> HTTPCaller__Rejected__5
HTTPCaller_Output_5: Inspector
HTTPCaller__Rejected__5: Inspector

FME custom transformer HoogspanningsnetQuerier

Parameters:
- X_MIN = @Value(x_min)   # X Min
- Y_MAX = @Value(y_max)   # Y Max
- Y_MIN = @Value(y_min)   # Y Min
- X_MAX = @Value(x_max)   # X Max
- LAYER = @Value(layer)   # layer

Query_parameters (input)
    -> HTTPCaller
Note: Herprojecteren naar RD_New
Reprojector
    DEST = EPSG:28992
    INTERPOLATION_TYPE_NAME = Nearest Neighbor
    RASTER_CELL_SIZE = Preserve Cells
    RASTER_TOLERANCE = 0.0
    SOURCE = Read from feature
    REPROJECTED -> Results (output)
Results (output)

Bookmark: Alle ID's ophalen
HTTPCaller
    ADDITIONAL_URL_PARAMETERS = type;@Value(layer) bbox;@Value(x_min),@Value(y_min),@Value(x_max),@Value(y_max) zoom;13
    CONNECTION_TIMEOUT_LENGTH = 60
    CUSTOM_HEADERS = accept;*/* referer;https://webkaart.hoogspanningsnet.com/index2.php user-agent;Mozilla/5.0 (Windows NT 10.0; Win64; x64) AppleWebKit/537.36 (KHTML, like Gecko) Chrome/71.0.3578.98 Safari/537.36 accept-encoding;gzip, deflate, br accept-language;nl-NL,nl;q=0.9,en-US;q=0.8,en;q=0.7
    ERROR_ATTR = _error
    FILE_PATH_ATTR = _response_file_path
    FOLLOW_REDIRECTS = Yes
    HTTP_METHOD = GET
    OUTPUT_FILENAME = hoogspanningsnet.geojson
    SAVE_FILE = File
    SAVE_MULTI = No
    STATUS_CODE_ATTR = _http_status_code
    TARGET_URL = https://webkaart.hoogspanningsnet.com/layerdata.php
    TRANSFER_TIMEOUT_LENGTH = 90
    USE_COOKIES = Yes
    VERIFY_SSL_CERTIFICATES = No
    -> FeatureReader [INITIATOR]
FeatureReader
    ATTR_ACCUM_MODE = Only Use Result
    COMBINE_GEOM = Use Result
    DATASET = @Value(_response_file_path)
    FORMAT = GEOJSON
    GEOJSON_FLATTEN_MODE = ALL_LEVELS
    GEOJSON_USE_BASENAME_AS_DEFAULT_FEATURE_TYPE = Yes
    GEOJSON_USE_SEARCH_ENVELOPE = NO
    INTERACT = Initiator Intersects Result
    OUTPUT_FEATURES_DISPLAY = Schema and Data Features
    <OTHER> -> AttributeExposer
AttributeExposer
    ATTR_LIST = ID,HoofdType
    -> HTTPCaller_2

Bookmark: Voor ieder ID detailinformatie ophalen
HTTPCaller_2
    ADDITIONAL_URL_PARAMETERS = ID;@Value(ID)
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://webkaart.hoogspanningsnet.com/balloon4.php
    TRANSFER_TIMEOUT_LENGTH = 90
    USE_COOKIES = No
    VERIFY_SSL_CERTIFICATES = No
    -> HTMLExtractor
HTMLExtractor
    HTML_FIELD = @Value(_response_body)
    HTML_SPECIFICATION = Content
    RESULT_TYPE_NAME = LIST_ATTR
    SEARCH_TABLE = Label .balloon-gegtitel Value Waarde .balloon-gegwaarde Value Big_label .balloon-bigtitel  Value Big_waarde .balloon-bigwaarde Value Opm_label .balloon-opmtitel Value Opm_waarde .balloon-opmwaarde Value Foto .balloon-foto src
    Results -> PythonCaller
PythonCaller
    PYTHONSOURCE:
      import fme
      import fmeobjects
      import re

      def extractListElements(feature):
          unlist(feature, 'Label', 'Waarde')

          unlist(feature, 'Opm_label', 'Opm_waarde')

          unlist(feature, 'Big_label', 'Big_waarde')

          foto = feature.getAttribute('Foto{0}')
          if foto != None:
              if foto[-18:].lower() != 'geenfoto_blank.png':
                  feature.setAttribute('Foto', foto)

      def unlist(f, l, w):
          i = 0
          while True:
              label = f.getAttribute(l + '{%d}' % i)
              if label == None:
                  break
              label = label.replace(" ", "_")
              value = f.getAttribute(w + '{%d}' % i)
              value = value.replace("</br>", "")
              value = value.replace("<br/>", "")
              value = value.replace("<br>", ", ")
              f.setAttribute(label, value)
              i += 1
    PYTHONSYMBOL = extractListElements
    -> AttributeRenamer

Bookmark: Resultaat opschonen
AttributeRenamer
    ATTR_TABLE = RENAME_SET_DEFAULT HoofdType > Hoofdtype
    -> AttributeRemover
AttributeRemover
    LIST_ATTRS = Big_label{} Foto{} Label{} Opm_label{} Opm_waarde{} Waarde{} Big_waarde{}
    REMOVE_ATTRS = _http_status_code,_response_body
    -> Reprojector

FME custom transformer DataloketUploader

Parameters:
- token = Bearer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.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.C5592fFwy3J3onV1ImVfrluOFdaWF_GE1ZcEfp_eiWY1VXEwQtqX1rV1y440eBlaTC4P9Y4sbps-_N1CbLvmRJVrXvBnBnN0G_bdgTS9hgXMIjFtjMa3eANsQuoMe7fGCqRTnE62oUC5qA_FNkpJzZrspO_zoZTaLoYLP2TpqbJg62j2WADQnfDUabR2vXtsoO0eX7ffmn2Cp4R2nLzimaAz6gKsCK7iAUefk2UDzBEMhOWsc6igezi_QSCsanWjSMF1JbsAGf6p-9fez3toDDBa9ksdEfM91ghex2im35spiHAfKYvdhvQIb0izMN1ceSq7yLHoC_c-OLVy-9aLvw   # Token
- CONTACTPERSOON = @Value(Contactpersoon)   # Contactpersoon
- OMSCHRIJVING = @Value(Omschrijving)   # Omschrijving
- TAGS = @Value(Tags)   # Tags
- TITEL = @Value(Titel)   # Titel
- TOEGANG = @Value(Toegang)   # Toegang
- THEMAS = @Value(Themas)   # Themas
- TYPE = @Value(Type)   # Type

Parameters (input)
    -> GeometryExtractor
Note: Geometrie opslaan als Well-Known Text
GeometryExtractor
    ATTR = _geometry
    KIND_LONG = OGC Well Known Text
    OGCVERSION = 1.2
    OGC_WKT_PRECISION_DISPLAY = 64-bit
    PREFER_POLYGON_OVER_SURFACE = No
    REMOVE_GEOMETRY = No
    -> FeatureWriter [Output]
Note: Features wegschrijven naar CSV-bestand
FeatureWriter
    CSV2_COORDINATE_SYSTEM_GRANULARITY = FEATURE_TYPE
    CSV2_DELIMITER = ,
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_WRITE_BOM_FOR_UNICODE = Yes
    CSV2_WRITE_FIELD_NAMES = firstrow
    CSV2_WRITE_SCHEMA_FILE = NO
    DATASET = $(FME_MF_DIR_USERTYPED)
    DATASET_ATTR = _dataset
    FEATURE_TYPE_LIST_ATTR = _feature_type
    FORMAT = CSV2
    TOTAL_FEATURES_WRITTEN_ATTR = _total_features_written
    SUMMARY -> HTTPCaller
Note: Bestand en metadata uploaden naar Dataloket
HTTPCaller
    CONNECTION_TIMEOUT_LENGTH = 60
    CUSTOM_HEADERS = Authorization;$(token) Host;xe5f95b82989a4b549abc16a-staging.azurewebsites.net
    ERROR_ATTR = _error
    FOLLOW_REDIRECTS = Yes
    HTTP_METHOD = POST
    MULTIPARTS = access StringUpload SOURCE_EXPRESSION;$(TOEGANG);MIME_TYPE;text/plain;FME_CONTROLLER_QUERY_FILE;transformers\dependencies\http\StringUpload.fme title StringUpload SOURCE_EXPRESSION;$(TITEL);MIME_TYPE;text/plain;FME_CONTROLLER_QUERY_FILE;transformers\dependencies\http\StringUpload.fme description StringUpload SOURCE_EXPRESSION;$(OMSCHRIJVING);MIME_TYPE;text/plain;FME_CONTROLLER_QUERY_FILE;transformers\dependencies\http\StringUpload.fme contentTypeName StringUpload SOURCE_EXPRESSION;$(TYPE);MIME_TYPE;text/plain;FME_CONTROLLER_QUERY_FILE;transformers\dependencies\http\StringUpload.fme sourceTags StringUpload SOURCE_EXPRESSION;$(TAGS);MIME_TYPE;text/plain;FME_CONTROLLER_QUERY_FILE;transformers\dependencies\http\StringUpload.fme themes StringUpload SOURCE_EXPRESSION;$(THEMAS);MIME_TYPE;text/plain;FME_CONTROLLER_QUERY_FILE;transformers\dependencies\http\StringUpload.fme contactPerson StringUpload SOURCE_EXPRESSION;$(CONTACTPERSOON);MIME_TYPE;text/plain;FME_CONTROLLER_QUERY_FILE;transformers\dependencies\http\StringUpload.fme document FileUpload SOURCE_FILE;@Value(_dataset)@Value(_feature_type{0}.name).csv;MIME_TYPE;text/plain;FME_CONTROLLER_QUERY_FILE;transformers\dependencies\http\FileUpload.fme
    SAVE_FILE = Attribute
    STATUS_CODE_ATTR = _http_status_code
    TARGET_ATTR = _response_body
    TARGET_ATTR_ENCODING = auto-detect
    TARGET_URL = https://dataloket.zuid-holland.nl/api/documents/upload
    TRANSFER_TIMEOUT_LENGTH = 90
    UPLOAD_TYPE = Multipart / Form Data
    USE_COOKIES = No
    VERIFY_SSL_CERTIFICATES = No
    -> AttributeRemover
    <REJECTED> -> AttributeRemover_2
AttributeRemover
    LIST_ATTRS = _feature_type{}
    REMOVE_ATTRS = _dataset,_total_features_written
    -> Output (output)
Output (output)
AttributeRemover_2
    LIST_ATTRS = _feature_type{}
    REMOVE_ATTRS = _dataset,_total_features_written
    -> <Rejected> (output)
<Rejected> (output)
