FME workspace hoogspanningsnet.com2fgdb.fmw
Title: Hoogspanningsnet.com2fgdb
Description: Workspace om de gegevens uit https://webkaart.hoogspanningsnet.com weg te schrijven naar een file geodatabase. 
Soms geeft de workspace een error. De website geeft de HTTPCaller een HTTP error 507 of 503 terug. De website is dan overbelast. Probeer het later nog een keer.
History: ,7-2-2019,Willy Tadema,

Parameters:
- DestDataset_GEODATABASE_FILE = T:\Databeheer Blauw\Werkplaats\Willy\test.gdb   # File Geodatabase
- SourceDataset_WFS = https://geodata.nationaalgeoregister.nl/bestuurlijkegrenzen/wfs?   # Source WFS (Web Feature Service) URL

Readers:
- WFS_1: WFS from $(SourceDataset_WFS)

Writers:
- GEODATABASE_FILE_1: GEODATABASE_FILE to $(DestDataset_GEODATABASE_FILE)

Note: Soms geeft de workspace een error. / De website geeft de HTTPCaller een HTTP error 507 of 503 terug. / De website is dan overbelast. Probeer het later nog een keer.
provincies (reader WFS_1)
    attributes: gml_parent_id xml_buffer, gml_parent_property xml_buffer, gml_id xml_buffer, gid xml_int32, gid.xsi_nil xml_boolean, provincienaam xml_buffer, provincienaam.xsi_nil xml_boolean, geom xml_geometry
    -> Reprojector
Reprojector
    DEST = EPSG:4326
    INTERPOLATION_TYPE_NAME = Nearest Neighbor
    RASTER_CELL_SIZE = Preserve Cells
    RASTER_TOLERANCE = 0.0
    SOURCE = Read from feature
    REPROJECTED -> BoundsExtractor
BoundsExtractor
    XMAX = x_max
    XMIN = x_min
    YMAX = y_max
    YMIN = y_min
    -> Junction
Junction
    -> HoogspanningsnetQuerier [Query_parameters] [off]
    -> HoogspanningsnetQuerier_2 [Query_parameters] [off]
    -> HoogspanningsnetQuerier_3 [Query_parameters] [off]
    -> HoogspanningsnetQuerier_4 [Query_parameters]
    -> HoogspanningsnetQuerier_5 [Query_parameters]
HoogspanningsnetQuerier [off]
    LAYER = mast
    X_MAX = @Value(x_max)
    X_MIN = @Value(x_min)
    Y_MAX = @Value(y_max)
    Y_MIN = @Value(y_min)
    Results -> AttributeExposer [off]
AttributeExposer [off]
    ATTR_LIST = Beheerder,Benutting,Bouwwijze,Hoofdtype,In_dienst,Land,Mastfunctie,Masthoogte,Mastmodel,Mastnummer,Naam,Spanning,Subtype,Verbinding,Opmerkingen,Foto,Circuits
    -> Hoogspanningsnet_masten (writer GEODATABASE_FILE_1) [off]
Hoogspanningsnet_masten (writer GEODATABASE_FILE_1) [off]
    attributes: Hoofdtype char(200), ID char(200), Beheerder char(200), Benutting char(200), Bouwwijze char(200), In_dienst char(200), Land char(200), Mastfunctie char(200), Masthoogte char(200), Mastmodel char(200), Mastnummer char(200), Naam char(200), Spanning char(200), Subtype char(200), Verbinding char(200), Opmerkingen char(200), Foto char(200), Circuits char(200)
HoogspanningsnetQuerier_2 [off]
    LAYER = terr
    X_MAX = @Value(x_max)
    X_MIN = @Value(x_min)
    Y_MAX = @Value(y_max)
    Y_MIN = @Value(y_min)
    Results -> AttributeExposer_2 [off]
AttributeExposer_2 [off]
    ATTR_LIST = Aantal_velden,Bedrijfsspanning,Beheerder,Beheerdercode,Beheerdernaam,Constructiewijze,Frequentie,Hoofdtype,Hoogste_spanning,In_dienst,Land,Naam,Railcapaciteit,Railconfiguratie,Spanning,Systeem,Opmerkingen,Foto
    -> Hoogspanningsnet_terreinen (writer GEODATABASE_FILE_1) [off]
Hoogspanningsnet_terreinen (writer GEODATABASE_FILE_1) [off]
    attributes: Hoofdtype char(200), ID char(200), Aantal_velden char(200), Bedrijfsspanning char(200), Beheerder char(200), Beheerdercode char(200), Beheerdernaam char(200), Constructiewijze char(200), Frequentie char(200), Hoogste_spanning char(200), In_dienst char(200), Land char(200), Naam char(200), Railcapaciteit char(200), Railconfiguratie char(200), Spanning char(200), Systeem char(200), Opmerkingen char(200), Foto char(200)
HoogspanningsnetQuerier_3 [off]
    LAYER = knpp
    X_MAX = @Value(x_max)
    X_MIN = @Value(x_min)
    Y_MAX = @Value(y_max)
    Y_MIN = @Value(y_min)
    Results -> AttributeExposer_3 [off]
AttributeExposer_3 [off]
    ATTR_LIST = Beheerder,IconPNG,In_dienst,Land,Naam,Netsituatie,Spanning,Opmerkingen,Foto
    -> AttributeManager [off]
AttributeManager [off]
    ATTR_TABLE:
      REMOVE Hoofdtype
      SET_TO IconPNG = https://webkaart.hoogspanningsnet.com/files/@Value(IconPNG)
    -> Hoogspanningsnet_knooppunten (writer GEODATABASE_FILE_1) [off]
Hoogspanningsnet_knooppunten (writer GEODATABASE_FILE_1) [off]
    attributes: ID char(200), Beheerder char(200), IconPNG char(200), In_dienst char(200), Land char(200), Naam char(200), Netsituatie char(200), Spanning char(200), Foto char(200), Opmerkingen char(200)
HoogspanningsnetQuerier_4
    LAYER = verb
    X_MAX = @Value(x_max)
    X_MIN = @Value(x_min)
    Y_MAX = @Value(y_max)
    Y_MIN = @Value(y_min)
    Results -> AttributeExposer_4
AttributeExposer_4
    ATTR_LIST = Bedrijfsspanning,Beheerder,Beheerdercode,Beheerdernummer,Constructiewijze,Deelnet,Frequentie,Hoofdtype,Hoogste_spanning,In_dienst,Land,Lengte,Naam,Spanning,Systeem,Transportcapaciteit,Opmerkingen,Foto
    -> Hoogspanningsnet_verbindingen (writer GEODATABASE_FILE_1)
Hoogspanningsnet_verbindingen (writer GEODATABASE_FILE_1)
    attributes: Hoofdtype char(200), ID char(200), Bedrijfsspanning char(200), Beheerder char(200), Beheerdercode char(200), Beheerdernummer char(200), Constructiewijze char(200), Deelnet char(200), Frequentie char(200), Hoogste_spanning char(200), In_dienst char(200), Land char(200), Lengte char(200), Naam char(200), Spanning char(200), Systeem char(200), Transportcapaciteit char(200), Opmerkingen char(200), Foto char(200)
HoogspanningsnetQuerier_5
    LAYER = stat
    X_MAX = @Value(x_max)
    X_MIN = @Value(x_min)
    Y_MAX = @Value(y_max)
    Y_MIN = @Value(y_min)
    Results -> AttributeExposer_5
AttributeExposer_5
    ATTR_LIST = Afkorting,Beheerder_primair,Beheerder_secundair,Hoofdtype,In_dienst,Land,Naam,Spanning,Spanningen,Type,Opmerkingen,Foto
    -> Hoogspanningsnet_stations (writer GEODATABASE_FILE_1)
Hoogspanningsnet_stations (writer GEODATABASE_FILE_1)
    attributes: Hoofdtype char(200), ID char(200), Afkorting char(200), Beheerder_primair char(200), Beheerder_secundair char(200), In_dienst char(200), Land char(200), Naam char(200), Spanning char(200), Spanningen char(200), Type char(200), Opmerkingen char(200), Foto char(200)

FME custom transformer HoogspanningsnetQuerier

Parameters:
- X_MIN = @Value(x_min)   # X Min
- Y_MAX = @Value(y_max)   # Y Max
- Y_MIN = @Value(y_min)   # Y Min
- X_MAX = @Value(x_max)   # X Max
- LAYER = @Value(layer)   # layer

Query_parameters (input)
    -> HTTPCaller
Note: Herprojecteren naar RD_New
Reprojector
    DEST = EPSG:28992
    INTERPOLATION_TYPE_NAME = Nearest Neighbor
    RASTER_CELL_SIZE = Preserve Cells
    RASTER_TOLERANCE = 0.0
    SOURCE = Read from feature
    REPROJECTED -> Results (output)
Results (output)

Bookmark: Alle ID's ophalen
HTTPCaller
    ADDITIONAL_URL_PARAMETERS = type;@Value(layer) bbox;@Value(x_min),@Value(y_min),@Value(x_max),@Value(y_max) zoom;13
    CONNECTION_TIMEOUT_LENGTH = 60
    CUSTOM_HEADERS = accept;*/* referer;https://webkaart.hoogspanningsnet.com/index2.php user-agent;Mozilla/5.0 (Windows NT 10.0; Win64; x64) AppleWebKit/537.36 (KHTML, like Gecko) Chrome/71.0.3578.98 Safari/537.36 accept-encoding;gzip, deflate, br accept-language;nl-NL,nl;q=0.9,en-US;q=0.8,en;q=0.7
    ERROR_ATTR = _error
    FILE_PATH_ATTR = _response_file_path
    FOLLOW_REDIRECTS = Yes
    HTTP_METHOD = GET
    OUTPUT_FILENAME = hoogspanningsnet.geojson
    SAVE_FILE = File
    SAVE_MULTI = No
    STATUS_CODE_ATTR = _http_status_code
    TARGET_URL = https://webkaart.hoogspanningsnet.com/layerdata.php
    TRANSFER_TIMEOUT_LENGTH = 90
    USE_COOKIES = Yes
    VERIFY_SSL_CERTIFICATES = No
    -> FeatureReader [INITIATOR]
FeatureReader
    ATTR_ACCUM_MODE = Only Use Result
    COMBINE_GEOM = Use Result
    DATASET = @Value(_response_file_path)
    FORMAT = GEOJSON
    GEOJSON_FLATTEN_MODE = ALL_LEVELS
    GEOJSON_USE_BASENAME_AS_DEFAULT_FEATURE_TYPE = Yes
    GEOJSON_USE_SEARCH_ENVELOPE = NO
    INTERACT = Initiator Intersects Result
    OUTPUT_FEATURES_DISPLAY = Schema and Data Features
    <OTHER> -> AttributeExposer
AttributeExposer
    ATTR_LIST = ID,HoofdType
    -> HTTPCaller_2

Bookmark: Voor ieder ID detailinformatie ophalen
HTTPCaller_2
    ADDITIONAL_URL_PARAMETERS = ID;@Value(ID)
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://webkaart.hoogspanningsnet.com/balloon4.php
    TRANSFER_TIMEOUT_LENGTH = 90
    USE_COOKIES = No
    VERIFY_SSL_CERTIFICATES = No
    -> HTMLExtractor
HTMLExtractor
    HTML_FIELD = @Value(_response_body)
    HTML_SPECIFICATION = Content
    RESULT_TYPE_NAME = LIST_ATTR
    SEARCH_TABLE = Label .balloon-gegtitel Value Waarde .balloon-gegwaarde Value Big_label .balloon-bigtitel  Value Big_waarde .balloon-bigwaarde Value Opm_label .balloon-opmtitel Value Opm_waarde .balloon-opmwaarde Value Foto .balloon-foto src
    Results -> PythonCaller
PythonCaller
    PYTHONSOURCE:
      import fme
      import fmeobjects
      import re

      def extractListElements(feature):
          unlist(feature, 'Label', 'Waarde')

          unlist(feature, 'Opm_label', 'Opm_waarde')

          unlist(feature, 'Big_label', 'Big_waarde')

          foto = feature.getAttribute('Foto{0}')
          if foto != None:
              if foto[-18:].lower() != 'geenfoto_blank.png':
                  feature.setAttribute('Foto', foto)

      def unlist(f, l, w):
          i = 0
          while True:
              label = f.getAttribute(l + '{%d}' % i)
              if label == None:
                  break
              label = label.replace(" ", "_")
              value = f.getAttribute(w + '{%d}' % i)
              value = value.replace("</br>", "")
              value = value.replace("<br/>", "")
              value = value.replace("<br>", ", ")
              f.setAttribute(label, value)
              i += 1
    PYTHONSYMBOL = extractListElements
    -> AttributeRenamer

Bookmark: Resultaat opschonen
AttributeRenamer
    ATTR_TABLE = RENAME_SET_DEFAULT HoofdType > Hoofdtype
    -> AttributeRemover
AttributeRemover
    LIST_ATTRS = Big_label{} Foto{} Label{} Opm_label{} Opm_waarde{} Waarde{} Big_waarde{}
    REMOVE_ATTRS = _http_status_code,_response_body
    -> Reprojector
