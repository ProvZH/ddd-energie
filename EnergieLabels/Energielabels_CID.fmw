FME workspace Energielabels_CID.fmw
Title: Energielabels CID-gebied

Parameters:
- SourceDataset_ESRISHAPE = https://github.com/ProvZH/ddd-energie/raw/master/Contour_CID/CID_grens.zip   # Source Esri Shapefile(s)
- SourceDataset_WFS_RIVM = http://geodata.rivm.nl/geoserver/nea/wfs?   # WFS RIVM
- DestDataset_GEODATABASE_FILE = T:\Databeheer Blauw\Werkplaats\Willy\test.gdb   # File Geodatabase

Readers:
- ESRISHAPE_1: ESRISHAPE from $(SourceDataset_ESRISHAPE)
- WFS_1: WFS from $(SourceDataset_WFS_RIVM)

Writers:
- GEODATABASE_FILE_1: GEODATABASE_FILE to $(DestDataset_GEODATABASE_FILE)

CID_grens (reader ESRISHAPE_1)
    attributes: focusgebie char(50), gemeente char(50)
    -> Dissolver
Dissolver
    ACCUM_INPUT_ATTRS = Use Attributes From One Feature
    CLEANING_TOLERANCE = None
    CONNECT_Z_MODE = First Wins
    DEAGGREGATE_INPUT = Yes
    NO_OVRLP = No
    AREA -> BoundsExtractor
    AREA -> SpatialFilter_2 [Filter]
    AREA -> SpatialFilter [Filter]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager
AttributeManager
    ATTR_TABLE:
      REMOVE gml_parent_id
      REMOVE gml_parent_property
      REMOVE gml_id
      REMOVE geom
      REMOVE pandid.xsi_nil
      REMOVE pandstatus.xsi_nil
      REMOVE bouwjaar.xsi_nil
      REMOVE pand_gebouwklasse.xsi_nil
      REMOVE energielabel.xsi_nil
      REMOVE aantal_verschillende_labels.xsi_nil
      REMOVE hoogste_label.xsi_nil
      REMOVE laagste_label.xsi_nil
      REMOVE tot_aantal_labels.xsi_nil
      REMOVE aantal_hoogste_labels.xsi_nil
      REMOVE aantal_laagste_labels.xsi_nil
      REMOVE _predicate
    -> Energielabels_utiliteitsbouw_CID (writer GEODATABASE_FILE_1)
Energielabels_utiliteitsbouw_CID (writer GEODATABASE_FILE_1)
    attributes: pandid char(2048), pandstatus char(2048), bouwjaar char(20), pand_gebouwklasse char(2048), energielabel char(2048), aantal_verschillende_labels integer, hoogste_label char(2048), laagste_label char(2048), tot_aantal_labels integer, aantal_hoogste_labels integer, aantal_laagste_labels integer, focusgebie char(50), gemeente char(50)
Note: Gebruikt voor specificeren envelope in parameters WFS reader
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager_2
AttributeManager_2
    ATTR_TABLE:
      REMOVE gml_parent_id
      REMOVE gml_parent_property
      REMOVE gml_id
      REMOVE geom
      REMOVE pandid.xsi_nil
      REMOVE pandstatus.xsi_nil
      REMOVE bouwjaar.xsi_nil
      REMOVE pand_gebouwklasse.xsi_nil
      REMOVE energielabel.xsi_nil
      REMOVE aantal_verschillende_labels.xsi_nil
      REMOVE hoogste_label.xsi_nil
      REMOVE laagste_label.xsi_nil
      REMOVE tot_aantal_labels.xsi_nil
      REMOVE aantal_hoogste_labels.xsi_nil
      REMOVE aantal_laagste_labels.xsi_nil
      REMOVE _predicate
    -> Energielabels_woningen_CID (writer GEODATABASE_FILE_1)
Energielabels_woningen_CID (writer GEODATABASE_FILE_1)
    attributes: pandid char(2048), pandstatus char(2048), bouwjaar char(20), pand_gebouwklasse char(2048), energielabel char(2048), aantal_verschillende_labels integer, hoogste_label char(2048), laagste_label char(2048), tot_aantal_labels integer, aantal_hoogste_labels integer, aantal_laagste_labels integer, focusgebie char(50), gemeente char(50)

Bookmark: Bounding box Oostland
BoundsExtractor [off]
    XMAX = _xmax
    XMIN = _xmin
    YMAX = _ymax
    YMIN = _ymin
    ZMAX = _zmax
    ZMIN = _zmin
    -> Boundingbox_CID [off]
Note: x_max = 84597.00010000542 / x_min = 81160.55409999937 / y_max = 456422.0000000037 / y_min = 453099.6370000057
Boundingbox_CID: Inspector [off]

Bookmark: Utilities
rvo_20181121_v_pand_energielabels_u (reader WFS_1)
    attributes: gml_parent_id xml_buffer, gml_parent_property xml_buffer, gml_id xml_buffer, geom xml_geometry, pandid xml_buffer, pandid.xsi_nil xml_boolean, pandstatus xml_buffer, pandstatus.xsi_nil xml_boolean, bouwjaar xml_int64, bouwjaar.xsi_nil xml_boolean, pand_gebouwklasse xml_buffer, pand_gebouwklasse.xsi_nil xml_boolean, energielabel xml_buffer, energielabel.xsi_nil xml_boolean, aantal_verschillende_labels xml_int32, aantal_verschillende_labels.xsi_nil xml_boolean, hoogste_label xml_buffer, hoogste_label.xsi_nil xml_boolean, laagste_label xml_buffer, laagste_label.xsi_nil xml_boolean, tot_aantal_labels xml_int32, tot_aantal_labels.xsi_nil xml_boolean, aantal_hoogste_labels xml_int32, aantal_hoogste_labels.xsi_nil xml_boolean, aantal_laagste_labels xml_int32, aantal_laagste_labels.xsi_nil xml_boolean
    -> SpatialFilter [Candidate]

Bookmark: Woningen
rvo_20181121_v_pand_energielabels_w (reader WFS_1)
    attributes: gml_parent_id xml_buffer, gml_parent_property xml_buffer, gml_id xml_buffer, geom xml_geometry, pandid xml_buffer, pandid.xsi_nil xml_boolean, pandstatus xml_buffer, pandstatus.xsi_nil xml_boolean, bouwjaar xml_int64, bouwjaar.xsi_nil xml_boolean, pand_gebouwklasse xml_buffer, pand_gebouwklasse.xsi_nil xml_boolean, energielabel xml_buffer, energielabel.xsi_nil xml_boolean, aantal_verschillende_labels xml_int32, aantal_verschillende_labels.xsi_nil xml_boolean, hoogste_label xml_buffer, hoogste_label.xsi_nil xml_boolean, laagste_label xml_buffer, laagste_label.xsi_nil xml_boolean, tot_aantal_labels xml_int32, tot_aantal_labels.xsi_nil xml_boolean, aantal_hoogste_labels xml_int32, aantal_hoogste_labels.xsi_nil xml_boolean, aantal_laagste_labels xml_int32, aantal_laagste_labels.xsi_nil xml_boolean
    -> SpatialFilter_2 [Candidate]
