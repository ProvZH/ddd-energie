FME workspace energielabels.fmw

Parameters:
- SourceDataset_WFS_RIVM = http://geodata.rivm.nl/geoserver/nea/wfs?   # WFS RIVM
- SourceDataset_WFS_BG = https://geodata.nationaalgeoregister.nl/bestuurlijkegrenzen/wfs?   # WFS Bestuurlijke Grenzen
- Provincie = Zuid-Holland
- DestDataset_GEOPACKAGE_2 = C:\Temp\energie_labels.gpkg   # GeoPackage File

Readers:
- WFS_1: WFS from $(SourceDataset_WFS_RIVM)
- WFS_2: WFS from $(SourceDataset_WFS_RIVM)
- WFS_3: WFS from $(SourceDataset_WFS_RIVM)
- WFS_4: WFS from $(SourceDataset_WFS_RIVM)
- WFS_5: WFS from $(SourceDataset_WFS_BG) in EPSG:28992

Writers:
- GEOPACKAGE_1: GEOPACKAGE to $(DestDataset_GEOPACKAGE_2)

Note: Bestuurlijke grens Zuid-Holland
provincies (reader WFS_5)
    attributes: gml_parent_id xml_buffer, gml_parent_property xml_buffer, gml_id xml_buffer, gid xml_int32, gid.xsi_nil xml_boolean, provincienaam xml_buffer, provincienaam.xsi_nil xml_boolean, geom xml_geometry
    -> SpatialFilter [Filter]
    -> SpatialFilter_2 [Filter]
Note: De service retourneert maximaal 1.000.000 features per request. Wij willen méér features opvragen. Hoe pakken we dat aan? / Hoewel de WFS van RIVM versie 2.0.0 is en volgens het Capabilities-document response paging wordt ondersteund, werkt het niet. / Als je paging probeert te gebruiken, krijg je de volgende foutmelding: / Cannot do natural order without a primary key, please add it or specify a manual sort over existing attributes / Als workaround knippen we de provincie Zuid-Holland op in vier geografische blokken met minder dan 1.000.000 features per blok.
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager
AttributeManager
    ATTR_TABLE:
      REMOVE geom
      REMOVE pandid.xsi_nil
      REMOVE pandstatus.xsi_nil
      REMOVE bouwjaar.xsi_nil
      REMOVE pand_gebouwklasse.xsi_nil
      REMOVE energielabel.xsi_nil
      REMOVE aantal_verschillende_labels.xsi_nil
      REMOVE hoogste_label.xsi_nil
      REMOVE laagste_label.xsi_nil
      REMOVE tot_aantal_labels.xsi_nil
      REMOVE aantal_hoogste_labels.xsi_nil
      REMOVE aantal_laagste_labels.xsi_nil
      REMOVE _predicate
    -> Energielabels_u (writer GEOPACKAGE_1)
Energielabels_u (writer GEOPACKAGE_1)
    attributes: provincienaam text, gml_parent_id text, gml_parent_property text, gml_id text, pandid text, pandstatus text, bouwjaar int, pand_gebouwklasse text, energielabel text, aantal_verschillende_labels mediumint, hoogste_label text, laagste_label text, tot_aantal_labels mediumint, aantal_hoogste_labels mediumint, aantal_laagste_labels mediumint
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager_2
AttributeManager_2
    ATTR_TABLE:
      REMOVE geom
      REMOVE pandid.xsi_nil
      REMOVE pandstatus.xsi_nil
      REMOVE bouwjaar.xsi_nil
      REMOVE pand_gebouwklasse.xsi_nil
      REMOVE energielabel.xsi_nil
      REMOVE aantal_verschillende_labels.xsi_nil
      REMOVE hoogste_label.xsi_nil
      REMOVE laagste_label.xsi_nil
      REMOVE tot_aantal_labels.xsi_nil
      REMOVE aantal_hoogste_labels.xsi_nil
      REMOVE aantal_laagste_labels.xsi_nil
      REMOVE _predicate
    -> Energielabels_w (writer GEOPACKAGE_1)
Energielabels_w (writer GEOPACKAGE_1)
    attributes: provincienaam text, gml_parent_id text, gml_parent_property text, gml_id text, pandid text, pandstatus text, bouwjaar int, pand_gebouwklasse text, energielabel text, aantal_verschillende_labels mediumint, hoogste_label text, laagste_label text, tot_aantal_labels mediumint, aantal_hoogste_labels mediumint, aantal_laagste_labels mediumint

Bookmark: Utilities
rvo_20181121_v_pand_energielabels_u (reader WFS_3) [off]
    attributes: gml_parent_id xml_buffer, gml_parent_property xml_buffer, gml_id xml_buffer, geom xml_geometry, pandid xml_buffer, pandid.xsi_nil xml_boolean, pandstatus xml_buffer, pandstatus.xsi_nil xml_boolean, bouwjaar xml_int64, bouwjaar.xsi_nil xml_boolean, pand_gebouwklasse xml_buffer, pand_gebouwklasse.xsi_nil xml_boolean, energielabel xml_buffer, energielabel.xsi_nil xml_boolean, aantal_verschillende_labels xml_int32, aantal_verschillende_labels.xsi_nil xml_boolean, hoogste_label xml_buffer, hoogste_label.xsi_nil xml_boolean, laagste_label xml_buffer, laagste_label.xsi_nil xml_boolean, tot_aantal_labels xml_int32, tot_aantal_labels.xsi_nil xml_boolean, aantal_hoogste_labels xml_int32, aantal_hoogste_labels.xsi_nil xml_boolean, aantal_laagste_labels xml_int32, aantal_laagste_labels.xsi_nil xml_boolean
    -> SpatialFilter [Candidate]
rvo_20181121_v_pand_energielabels_u (reader WFS_4) [off]
    attributes: gml_parent_id xml_buffer, gml_parent_property xml_buffer, gml_id xml_buffer, geom xml_geometry, pandid xml_buffer, pandid.xsi_nil xml_boolean, pandstatus xml_buffer, pandstatus.xsi_nil xml_boolean, bouwjaar xml_int64, bouwjaar.xsi_nil xml_boolean, pand_gebouwklasse xml_buffer, pand_gebouwklasse.xsi_nil xml_boolean, energielabel xml_buffer, energielabel.xsi_nil xml_boolean, aantal_verschillende_labels xml_int32, aantal_verschillende_labels.xsi_nil xml_boolean, hoogste_label xml_buffer, hoogste_label.xsi_nil xml_boolean, laagste_label xml_buffer, laagste_label.xsi_nil xml_boolean, tot_aantal_labels xml_int32, tot_aantal_labels.xsi_nil xml_boolean, aantal_hoogste_labels xml_int32, aantal_hoogste_labels.xsi_nil xml_boolean, aantal_laagste_labels xml_int32, aantal_laagste_labels.xsi_nil xml_boolean
    -> SpatialFilter [Candidate]
rvo_20181121_v_pand_energielabels_u (reader WFS_1) [off]
    attributes: gml_parent_id xml_buffer, gml_parent_property xml_buffer, gml_id xml_buffer, geom xml_geometry, pandid xml_buffer, pandid.xsi_nil xml_boolean, pandstatus xml_buffer, pandstatus.xsi_nil xml_boolean, bouwjaar xml_int64, bouwjaar.xsi_nil xml_boolean, pand_gebouwklasse xml_buffer, pand_gebouwklasse.xsi_nil xml_boolean, energielabel xml_buffer, energielabel.xsi_nil xml_boolean, aantal_verschillende_labels xml_int32, aantal_verschillende_labels.xsi_nil xml_boolean, hoogste_label xml_buffer, hoogste_label.xsi_nil xml_boolean, laagste_label xml_buffer, laagste_label.xsi_nil xml_boolean, tot_aantal_labels xml_int32, tot_aantal_labels.xsi_nil xml_boolean, aantal_hoogste_labels xml_int32, aantal_hoogste_labels.xsi_nil xml_boolean, aantal_laagste_labels xml_int32, aantal_laagste_labels.xsi_nil xml_boolean
    -> SpatialFilter [Candidate]
rvo_20181121_v_pand_energielabels_u (reader WFS_2)
    attributes: gml_parent_id xml_buffer, gml_parent_property xml_buffer, gml_id xml_buffer, geom xml_geometry, pandid xml_buffer, pandid.xsi_nil xml_boolean, pandstatus xml_buffer, pandstatus.xsi_nil xml_boolean, bouwjaar xml_int64, bouwjaar.xsi_nil xml_boolean, pand_gebouwklasse xml_buffer, pand_gebouwklasse.xsi_nil xml_boolean, energielabel xml_buffer, energielabel.xsi_nil xml_boolean, aantal_verschillende_labels xml_int32, aantal_verschillende_labels.xsi_nil xml_boolean, hoogste_label xml_buffer, hoogste_label.xsi_nil xml_boolean, laagste_label xml_buffer, laagste_label.xsi_nil xml_boolean, tot_aantal_labels xml_int32, tot_aantal_labels.xsi_nil xml_boolean, aantal_hoogste_labels xml_int32, aantal_hoogste_labels.xsi_nil xml_boolean, aantal_laagste_labels xml_int32, aantal_laagste_labels.xsi_nil xml_boolean
    -> SpatialFilter [Candidate]

Bookmark: Woningen
rvo_20181121_v_pand_energielabels_w (reader WFS_3) [off]
    attributes: gml_parent_id xml_buffer, gml_parent_property xml_buffer, gml_id xml_buffer, geom xml_geometry, pandid xml_buffer, pandid.xsi_nil xml_boolean, pandstatus xml_buffer, pandstatus.xsi_nil xml_boolean, bouwjaar xml_int64, bouwjaar.xsi_nil xml_boolean, pand_gebouwklasse xml_buffer, pand_gebouwklasse.xsi_nil xml_boolean, energielabel xml_buffer, energielabel.xsi_nil xml_boolean, aantal_verschillende_labels xml_int32, aantal_verschillende_labels.xsi_nil xml_boolean, hoogste_label xml_buffer, hoogste_label.xsi_nil xml_boolean, laagste_label xml_buffer, laagste_label.xsi_nil xml_boolean, tot_aantal_labels xml_int32, tot_aantal_labels.xsi_nil xml_boolean, aantal_hoogste_labels xml_int32, aantal_hoogste_labels.xsi_nil xml_boolean, aantal_laagste_labels xml_int32, aantal_laagste_labels.xsi_nil xml_boolean
    -> SpatialFilter_2 [Candidate]
rvo_20181121_v_pand_energielabels_w (reader WFS_4) [off]
    attributes: gml_parent_id xml_buffer, gml_parent_property xml_buffer, gml_id xml_buffer, geom xml_geometry, pandid xml_buffer, pandid.xsi_nil xml_boolean, pandstatus xml_buffer, pandstatus.xsi_nil xml_boolean, bouwjaar xml_int64, bouwjaar.xsi_nil xml_boolean, pand_gebouwklasse xml_buffer, pand_gebouwklasse.xsi_nil xml_boolean, energielabel xml_buffer, energielabel.xsi_nil xml_boolean, aantal_verschillende_labels xml_int32, aantal_verschillende_labels.xsi_nil xml_boolean, hoogste_label xml_buffer, hoogste_label.xsi_nil xml_boolean, laagste_label xml_buffer, laagste_label.xsi_nil xml_boolean, tot_aantal_labels xml_int32, tot_aantal_labels.xsi_nil xml_boolean, aantal_hoogste_labels xml_int32, aantal_hoogste_labels.xsi_nil xml_boolean, aantal_laagste_labels xml_int32, aantal_laagste_labels.xsi_nil xml_boolean
    -> SpatialFilter_2 [Candidate]
rvo_20181121_v_pand_energielabels_w (reader WFS_1) [off]
    attributes: gml_parent_id xml_buffer, gml_parent_property xml_buffer, gml_id xml_buffer, geom xml_geometry, pandid xml_buffer, pandid.xsi_nil xml_boolean, pandstatus xml_buffer, pandstatus.xsi_nil xml_boolean, bouwjaar xml_int64, bouwjaar.xsi_nil xml_boolean, pand_gebouwklasse xml_buffer, pand_gebouwklasse.xsi_nil xml_boolean, energielabel xml_buffer, energielabel.xsi_nil xml_boolean, aantal_verschillende_labels xml_int32, aantal_verschillende_labels.xsi_nil xml_boolean, hoogste_label xml_buffer, hoogste_label.xsi_nil xml_boolean, laagste_label xml_buffer, laagste_label.xsi_nil xml_boolean, tot_aantal_labels xml_int32, tot_aantal_labels.xsi_nil xml_boolean, aantal_hoogste_labels xml_int32, aantal_hoogste_labels.xsi_nil xml_boolean, aantal_laagste_labels xml_int32, aantal_laagste_labels.xsi_nil xml_boolean
    -> SpatialFilter_2 [Candidate]
rvo_20181121_v_pand_energielabels_w (reader WFS_2)
    attributes: gml_parent_id xml_buffer, gml_parent_property xml_buffer, gml_id xml_buffer, geom xml_geometry, pandid xml_buffer, pandid.xsi_nil xml_boolean, pandstatus xml_buffer, pandstatus.xsi_nil xml_boolean, bouwjaar xml_int64, bouwjaar.xsi_nil xml_boolean, pand_gebouwklasse xml_buffer, pand_gebouwklasse.xsi_nil xml_boolean, energielabel xml_buffer, energielabel.xsi_nil xml_boolean, aantal_verschillende_labels xml_int32, aantal_verschillende_labels.xsi_nil xml_boolean, hoogste_label xml_buffer, hoogste_label.xsi_nil xml_boolean, laagste_label xml_buffer, laagste_label.xsi_nil xml_boolean, tot_aantal_labels xml_int32, tot_aantal_labels.xsi_nil xml_boolean, aantal_hoogste_labels xml_int32, aantal_hoogste_labels.xsi_nil xml_boolean, aantal_laagste_labels xml_int32, aantal_laagste_labels.xsi_nil xml_boolean
    -> SpatialFilter_2 [Candidate]
