FME workspace schattingen-glastuinbouw-oostland-naar-fgdb.fmw
Title: Schattingen glastuinbouw Oostland naar file geodatabase
Description: Schattingen glastuinbouw Oostland (XLSX-formaat) importeren in twee feature classes in een file geodatabase: één met alle attributen gekoppeld aan vlakken en één gekoppeld aan punten (centroïden).
History: ,31-1-2019,WIlly Tadema,

Parameters:
- DestDataset_GEODATABASE_FILE = T:\Databeheer Blauw\Werkplaats\Willy\test.gdb   # File Geodatabase
- SourceDataset_XLSXR = $(FME_MF_DIR)20190131-schattingen-glastuinbouw-oostland.xlsx   # Source Microsoft Excel File(s)

Readers:
- XLSXR_1: XLSXR from $(SourceDataset_XLSXR) in EPSG:4326

Writers:
- GEODATABASE_FILE_1: GEODATABASE_FILE to $(DestDataset_GEODATABASE_FILE)

Data (reader XLSXR_1)
    attributes: objectid_1 number(5,0), straatnaam char(44), huisnummer char(21), bedr_naam char(53), gebruikkas char(26), teeltsoort char(17), teelt char(40), ondergrtlt char(17), kastype_1 char(12), poothgt1 number(4,1), kastype_2 char(12), poothgt2 number(4,1), leeftydkas number(5,0), verstening char(25), oppversten number(6,0), typversten char(24), besgrvers char(52), opmkas_sch char(73), belichting char(15), stomen char(9), co2noodzak char(9), co2bron char(21), wkk char(28), wkk_type char(24), wkkvermkw char(9), rgr char(9), warmbuiten char(25), bronwarmbu char(42), geothermie char(4), warmtebron char(11),
      koudebron char(29), buffer char(11), typebuffer char(18), vermbuff char(9), dockshelt char(9), scherm char(4), f_schermen char(9), typescherm char(42), zonnepan char(4), windmolen char(4), watbassin char(9), water_tank char(4), arbeidsint char(10), seizoen char(9), hnt char(9), enercode number(2,0), enerwarm char(70), opmenergie char(111), opmerking char(81), deelgebied number(2,0), registrati string, straat string, kern string, bagid string, poothoogt1 string, oppervlakt number(12,5), objectid number(9,0), identifica datetime, bouwjaar number(5,0), status char(33),
      shape_leng number(14,9), k_id number(6,0), plantsoort string, teeltc string, teeltd string, wateropslg string, ol0wl1 number(2,0), postcode char(7), pc6 char(7), aantal_mul number(2,0), aantal_adr number(4,0), id number(4,0), code number(5,0), gemeentena char(19), shape_le_1 number(14,9), shape_area number(15,8), geometry char(5044), centroid char(44), lat y_coordinate, lon x_coordinate
    -> AttributeRemover
    -> GeometryReplacer
AttributeRemover
    REMOVE_ATTRS = geometry,centroid,objectid,shape_leng,shape_area,shape_le_1,objectid_1
    -> Reprojector
Reprojector
    DEST = EPSG:28992
    INTERPOLATION_TYPE_NAME = Nearest Neighbor
    RASTER_CELL_SIZE = Preserve Cells
    RASTER_TOLERANCE = 0.0
    SOURCE = Read from feature
    REPROJECTED -> Schattingen_glastuinbouw_Oostland_punten (writer GEODATABASE_FILE_1)
Schattingen_glastuinbouw_Oostland_punten (writer GEODATABASE_FILE_1)
    attributes: straatnaam char(44), huisnummer char(21), bedr_naam char(53), gebruikkas char(26), teeltsoort char(17), teelt char(40), ondergrtlt char(17), kastype_1 char(12), poothgt1 double(4,1), kastype_2 char(12), poothgt2 double(4,1), leeftydkas integer, verstening char(25), oppversten integer, typversten char(24), besgrvers char(52), opmkas_sch char(73), belichting char(15), stomen char(9), co2noodzak char(9), co2bron char(21), wkk char(28), wkk_type char(24), wkkvermkw char(9), rgr char(9), warmbuiten char(25), bronwarmbu char(42), geothermie char(4), warmtebron char(11), koudebron char(29),
      buffer char(11), typebuffer char(18), vermbuff char(9), dockshelt char(9), scherm char(4), f_schermen char(9), typescherm char(42), zonnepan char(4), windmolen char(4), watbassin char(9), water_tank char(4), arbeidsint char(10), seizoen char(9), hnt char(9), enercode smallint, enerwarm char(70), opmenergie char(111), opmerking char(81), deelgebied smallint, registrati char(2048), straat char(2048), kern char(2048), bagid char(2048), poothoogt1 char(2048), oppervlakt double(12,5), identifica date, bouwjaar integer, status char(33), k_id integer, plantsoort char(2048),
      teeltc char(2048), teeltd char(2048), wateropslg char(2048), ol0wl1 smallint, postcode char(7), pc6 char(7), aantal_mul smallint, aantal_adr smallint, id smallint, code integer, gemeentena char(19), lat double, lon double
GeometryReplacer
    KIND_LONG = OGC Well Known Text
    OGC_WKT_PRECISION_DISPLAY = 64-bit
    REMOVE_ATTRIBUTE = Yes
    SOURCE = @Value(geometry)
    -> AttributeRemover_2
AttributeRemover_2
    REMOVE_ATTRS = centroid,objectid,shape_leng,shape_area,shape_le_1,objectid_1
    -> Reprojector_2
Reprojector_2
    DEST = EPSG:28992
    INTERPOLATION_TYPE_NAME = Nearest Neighbor
    RASTER_CELL_SIZE = Preserve Cells
    RASTER_TOLERANCE = 0.0
    SOURCE = Read from feature
    REPROJECTED -> Schattingen_glastuinbouw_Oostland_vlakken (writer GEODATABASE_FILE_1)
Schattingen_glastuinbouw_Oostland_vlakken (writer GEODATABASE_FILE_1)
    attributes: straatnaam char(44), huisnummer char(21), bedr_naam char(53), gebruikkas char(26), teeltsoort char(17), teelt char(40), ondergrtlt char(17), kastype_1 char(12), poothgt1 double(4,1), kastype_2 char(12), poothgt2 double(4,1), leeftydkas integer, verstening char(25), oppversten integer, typversten char(24), besgrvers char(52), opmkas_sch char(73), belichting char(15), stomen char(9), co2noodzak char(9), co2bron char(21), wkk char(28), wkk_type char(24), wkkvermkw char(9), rgr char(9), warmbuiten char(25), bronwarmbu char(42), geothermie char(4), warmtebron char(11), koudebron char(29),
      buffer char(11), typebuffer char(18), vermbuff char(9), dockshelt char(9), scherm char(4), f_schermen char(9), typescherm char(42), zonnepan char(4), windmolen char(4), watbassin char(9), water_tank char(4), arbeidsint char(10), seizoen char(9), hnt char(9), enercode smallint, enerwarm char(70), opmenergie char(111), opmerking char(81), deelgebied smallint, registrati char(2048), straat char(2048), kern char(2048), bagid char(2048), poothoogt1 char(2048), oppervlakt double(12,5), identifica date, bouwjaar integer, status char(33), k_id integer, plantsoort char(2048),
      teeltc char(2048), teeltd char(2048), wateropslg char(2048), ol0wl1 smallint, postcode char(7), pc6 char(7), aantal_mul smallint, aantal_adr smallint, id smallint, code integer, gemeentena char(19), lat double, lon double
