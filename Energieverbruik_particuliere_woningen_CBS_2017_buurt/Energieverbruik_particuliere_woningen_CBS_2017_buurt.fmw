FME workspace Energieverbruik_particuliere_woningen_CBS_2017_buurt.fmw
Title: Energieverbruik_particuliere_woningen_2017
Description: Workspace voor het inlezen van CBS-dataset 84314NED en wegschrijven naar een file geodatabase.
History: ,12-2-2019,Willy Tadema,

Parameters:
- DestDataset_GEODATABASE_FILE = T:\Databeheer Blauw\Werkplaats\Willy\test.gdb   # File Geodatabase
- SourceDataset_WFS = https://geodata.nationaalgeoregister.nl/bestuurlijkegrenzen/wfs?   # Source WFS (Web Feature Service) URL

Readers:
- WFS_1: WFS from $(SourceDataset_WFS)

Writers:
- GEODATABASE_FILE_1: GEODATABASE_FILE to $(DestDataset_GEODATABASE_FILE) in EPSG:28992

Note: Inlezen van CBS-dataset 84314NED (Energieverbruik particuliere woningen 2017) voor alle buurten in de provincie Zuid-Holland
Note: OData reader werkt niet, vandaar deze workaround. / Zie https://knowledge.safe.com/questions/59276/importing-odata-feed-with-https-url.html
FeatureMerger
    ATTR_ACCUM_MODE = Merge Supplier
    ATTR_CONFLICT_RES = Use Requestor
    IGNORE_NULLS = No
    JOIN_KEYS = @Value(Codering) @Value(buurtcode) AUTO
    MERGE_TYPE = Attributes and Geometry
    PROCESS_DUPS = NO
    REJECT_NULL_MISSING_KEYS = No
    SUPPLIERS_FIRST = No
    MERGED -> Energieverbruik_particuliere_woningen_CBS_2017_buurt (writer GEODATABASE_FILE_1)
Energieverbruik_particuliere_woningen_CBS_2017_buurt (writer GEODATABASE_FILE_1)
    attributes: buurtcode char(200), buurtnaam char(200), gemeentecode char(200), gemeentenaam char(200), wijkcode char(200), ID char(200), Woningkenmerken char(200), WijkenEnBuurten char(200), SoortRegio char(200), Codering char(200), GemiddeldAardgasverbruik_m3 char(200), GemiddeldElektriciteitsverbruik_kWh char(200), Stadsverwarming_perc char(200), IndelingswijzigingWijkenEnBuurten char(200), Woningkenmerken_label char(200)

Bookmark: Provinciegrens met kleine buffer
provincies (reader WFS_1)
    attributes: gml_parent_id xml_buffer, gml_parent_property xml_buffer, gml_id xml_buffer, gid xml_int32, gid.xsi_nil xml_boolean, provincienaam xml_buffer, provincienaam.xsi_nil xml_boolean, geom xml_geometry
    -> Bufferer
Bufferer
    ANGLE = 22.5
    CAP_STYLE = Round
    CORNER_STYLE = Round
    MODE = AREA
    OFFSET = 100
    BUFFERED -> FeatureReader [INITIATOR]

Bookmark: Buurten in de provincie Zuid-Holland
FeatureReader
    ATTRIBUTES = cbs_buurten_2017,"gml_parent_id,gml_parent_property,gml_id,aantal_inwoners,aantal_inwoners.xsi_nil,mannen,mannen.xsi_nil,vrouwen,vrouwen.xsi_nil,aantal_huishoudens,aantal_huishoudens.xsi_nil,bevolkingsdichtheid_inwoners_per_km2,bevolkingsdichtheid_inwoners_per_km2.xsi_nil,buurtcode,buurtcode.xsi_nil,buurtnaam,buurtnaam.xsi_nil,dekkingspercentage,dekkingspercentage.xsi_nil,gemiddelde_huishoudsgrootte,gemiddelde_huishoudsgrootte.xsi_nil,gemeentecode,gemeentecode.xsi_nil,gemeentenaam,gemeentenaam.xsi_nil,indelingswijziging_wijken_en_buurten_indicator,indelingswijziging_wijken_en_buurten_indicator.xsi_nil,omgevingsadressendichtheid,omgevingsadressendichtheid.xsi_nil,oppervlakte_land_in_ha,oppervlakte_land_in_ha.xsi_nil,oppervlakte_totaal_in_ha,oppervlakte_totaal_in_ha.xsi_nil,oppervlakte_water_in_ha,oppervlakte_water_in_ha.xsi_nil,percentage_personen_0_tot_15_jaar,percentage_personen_0_tot_15_jaar.xsi_nil,percentage_personen_15_tot_25_jaar,percentage_personen_15_tot_25_jaar.xsi_nil,percentage_personen_25_tot_45_jaar,percentage_personen_25_tot_45_jaar.xsi_nil,percentage_personen_45_tot_65_jaar,percentage_personen_45_tot_65_jaar.xsi_nil,percentage_personen_65_jaar_en_ouder,percentage_personen_65_jaar_en_ouder.xsi_nil,percentage_uit_nederlandse_antillen_en_aruba,percentage_uit_nederlandse_antillen_en_aruba.xsi_nil,percentage_eenpersoonshuishoudens,percentage_eenpersoonshuishoudens.xsi_nil,percentage_gehuwd,percentage_gehuwd.xsi_nil,percentage_gescheid,percentage_gescheid.xsi_nil,percentage_huishoudens_met_kinderen,percentage_huishoudens_met_kinderen.xsi_nil,percentage_huishoudens_zonder_kinderen,percentage_huishoudens_zonder_kinderen.xsi_nil,percentage_uit_marokko,percentage_uit_marokko.xsi_nil,percentage_niet_westerse_allochtonen,percentage_niet_westerse_allochtonen.xsi_nil,percentage_ongehuwd,percentage_ongehuwd.xsi_nil,percentage_overige_niet_westerse_allochtonen,percentage_overige_niet_westerse_allochtonen.xsi_nil,percentage_uit_suriname,percentage_uit_suriname.xsi_nil,percentage_uit_turkije,percentage_uit_turkije.xsi_nil,percentage_verweduwd,percentage_verweduwd.xsi_nil,percentage_westerse_allochtonen,percentage_westerse_allochtonen.xsi_nil,meest_voorkomende_postcode,meest_voorkomende_postcode.xsi_nil,stedelijkheid_adressen_per_km2,stedelijkheid_adressen_per_km2.xsi_nil,water,water.xsi_nil,wijkcode,wijkcode.xsi_nil,geom,fme_geometry{0},fme_geometry{1}"
    ATTR_ACCUM_MODE = Only Use Result
    COMBINE_GEOM = Use Result
    DATASET = https://geodata.nationaalgeoregister.nl/wijkenbuurten2017/wfs?&request=GetCapabilities&service=WFS
    FEATURETYPES = cbs_buurten_2017
    FORMAT = WFS
    INTERACT = Initiator Contains Result
    OUTPUT_FEATURES_DISPLAY = Schema and Data Features
    WFS_CONNECTION_TIMEOUT = 90
    WFS_DISABLE_AUTOMATIC_READER_TYPE_SELECTION = NO
    WFS_DISABLE_XML_NAMESPACE_PROCESSING = NO
    WFS_ENFORCE_PATH_CONTINUITY_BY = SNAPPING_END_POINTS
    WFS_FLATTEN_XML_FRAGMENTS = NO
    WFS_IGNORE_APPLICATON_SCHEMA = no
    WFS_LOCAL_CACHE_EXPIRY = 60
    WFS_MAP_COMPLEX_PROPERTIES_AS = Nested Attributes
    WFS_MAP_EMBEDDED_OBJECTS_AS = ATTRIBUTES
    WFS_MAP_GEOMETRY_COLUMNS = YES
    WFS_MAP_PREDEFINED_GML_PROPERTIES = NO
    WFS_PREFERRED_VERSION = 1.0.0
    WFS_PREFER_DATASET_URL = No
    WFS_PREFER_POST = No
    WFS_TRANSFER_TIMEOUT = 90
    WFS_USE_OLD_READER = NO
    WFS_USE_SEARCH_ENVELOPE = NO
    WFS_XML_FRAGMENTS_AS_DOCUMENTS = YES
    cbs_buurten_2017 -> AttributeKeeper
AttributeKeeper
    KEEP_ATTRS = gemeentenaam,wijkcode,buurtnaam,buurtcode,gemeentecode
    -> FeatureMerger [SUPPLIER]

Bookmark: Aantal request dat nodig is om de hele dataset op te vragen
Creator
    GEOMTYPE = Geometry Object
    NUM = 1
    CREATED -> HTTPCaller
HTTPCaller
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = count
    TARGET_ATTR_ENCODING = auto-detect
    TARGET_URL = https://opendata.cbs.nl/ODataFeed/odata/84314NED/TypedDataSet/$count
    TRANSFER_TIMEOUT_LENGTH = 90
    USE_COOKIES = No
    VERIFY_SSL_CERTIFICATES = No
    -> Cloner
Cloner
    COPIES = @ceil(@Evaluate(@Value(count) / 10000))
    COPYATT = number
    COPY -> AttributeCreator

Bookmark: Dataset inlezen
AttributeCreator
    ATTR_TABLE = SET_TO request = FME_CONDITIONAL:DEFAULT_VALUE'https://opendata.cbs.nl/ODataFeed/odata/84314NED/TypedDataSet?$format=json&$skip=@Evaluate(@Value(number)*10000)'BOOL_OP;OR;COMPOSITE_TEST;<Unused>;TEST @Value(number) = 0'https://opendata.cbs.nl/ODataFeed/odata/84314NED/TypedDataSet?$format=json'FME_NUM_CONDITIONS2___
    -> HTTPCaller_2
HTTPCaller_2
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = _response_body
    TARGET_ATTR_ENCODING = auto-detect
    TARGET_URL = @Value(request)
    TRANSFER_TIMEOUT_LENGTH = 90
    USE_COOKIES = No
    VERIFY_SSL_CERTIFICATES = No
    -> JSONFragmenter
JSONFragmenter
    EXPLODE_FORMAT = JSON
    EXTRACT_ATTR = Yes
    JSON_ATTR = _response_body
    JSON_QUERY = json["value"][*]
    NEW_ATTRIBUTES = ID Woningkenmerken WijkenEnBuurten Gemeentenaam_1 SoortRegio_2 Codering_3 GemiddeldAardgasverbruik_4 GemiddeldElektriciteitsverbruik_5 Stadsverwarming_6 IndelingswijzigingWijkenEnBuurten_7
    READ_FROM_FILE = NO
    RECURSIVE = Yes
    REJECT_EMPTY_LISTS = YES
    FRAGMENTS -> AttributeManager
AttributeManager
    ATTR_TABLE:
      REMOVE request
      REMOVE _creation_instance
      REMOVE _headers{}.name
      REMOVE _headers{}.value
      REMOVE count
      REMOVE _http_status_code
      REMOVE number
      REMOVE _response_body
      REMOVE json_type
      REMOVE json_index
      RENAME_SET_VALUE Gemeentenaam_1 > Gemeentenaam
      RENAME_SET_VALUE SoortRegio_2 > SoortRegio
      RENAME_SET_VALUE Codering_3 > Codering
      RENAME_SET_VALUE GemiddeldAardgasverbruik_4 > GemiddeldAardgasverbruik_m3
      RENAME_SET_VALUE GemiddeldElektriciteitsverbruik_5 > GemiddeldElektriciteitsverbruik_kWh
      RENAME_SET_VALUE Stadsverwarming_6 > Stadsverwarming_perc
      RENAME_SET_VALUE IndelingswijzigingWijkenEnBuurten_7 > IndelingswijzigingWijkenEnBuurten
    -> AttributeValueMapper
AttributeValueMapper
    DIRECTION = Forward (Source To Destination)
    LUT = a,Totaal woningen,b,Appartement,c,Tussenwoning,d,Hoekwoning,e,Twee-onder-één-kap woning,f,Vrijstaande woning,g,Eigen woning,h,Huurwoning
    SRC = Woningkenmerken
    VAL_ATTR = Woningkenmerken_label
    -> FeatureMerger [REQUESTOR]
